-- Extracted by spec/tools/docx_asn1.py 1.0 from 3GPP TS 38.331 j40 (38331-j40.zip, sha256 908f5db632f8a999e078a404791ed739a3a1004f619bf2fc20c1ffd9747718b3).
-- Do not edit: regenerate with spec/tools/docx_asn1.py. Text (c) 3GPP; see spec/INDEX.tsv for the source.

NR-InterNodeDefinitions DEFINITIONS AUTOMATIC TAGS ::=

BEGIN

IMPORTS
    AffectedCarrierFreqCombList-r16,
    AffectedCarrierFreqRangeCombList-r18,
    ApplicabilityReportList-r19,
    ARFCN-ValueNR,
    ARFCN-ValueEUTRA,
    CandidateServingFreqListNR-r16,
    CandidateServingFreqRangeListNR-r18,
    CellIdentity,
    CGI-InfoEUTRA,
    CGI-InfoNR,
    CondReconfigExecCondSCG-r17,
    CSI-RS-Index,
    CSI-RS-CellMobility,
    DRX-Config,
    EUTRA-PhysCellId,
    FeatureSetDownlinkPerCC-Id,
    FeatureSetUplinkPerCC-Id,
    FlightPathInfoReport-r18,
    FreqBandIndicatorNR,
    GapConfig,
    IDC-TDM-Assistance-r18,
    maxBandComb,
    maxBands,
    maxBandsEUTRA,
    maxCandidateBandIndex-r18,
    maxCellSFTD,
    maxFeatureSetsPerBand,
    maxFreq,
    maxFreqIDC-MRDC,
    maxNrofCombIDC,
    maxNrofCondCells-r16,
    maxNrofCondCells-1-r17,
    maxNrofPhysicalResourceBlocks,
    maxNrofSCells,
    maxNrofServingCells,
    maxNrofServingCells-1,
    maxNrofServingCellsEUTRA,
    maxNrofIndexesToReport,
    maxNrofLTM-Configs-r18,
    maxSimultaneousBands,
    MBSInterestIndication-r17,
    MeasQuantityResults,
    MeasResultCellListSFTD-EUTRA,
    MeasResultCellListSFTD-NR,
    MeasResultList2NR,
    MeasResultSCG-Failure,
    MeasResultServFreqListEUTRA-SCG,
    MUSIM-CandidateBandList-r18,
    MUSIM-CapRestriction-r18,
    MUSIM-GapConfig-r17,
    NeedForGapsInfoNR-r16,
    NeedForGapNCSG-InfoNR-r17,
    NeedForGapNCSG-InfoEUTRA-r17,
    NeedForInterruptionInfoNR-r18,
    OverheatingAssistance,
    OverheatingAssistance-r17,
    P-Max,
    PhysCellId,
    RadioBearerConfig,
    RAN-NotificationAreaInfo,
    ReferenceConfiguration-r18,
    ReportConfigNR,
    RRCReconfiguration,
    ServCellIndex,
    SetupRelease,
    SSB-Index,
    SSB-MTC,
    SSB-ToMeasure,
    SS-RSSI-Measurement,
    ShortMAC-I,
    SubcarrierSpacing,
    UEAssistanceInformation,
    UE-CapabilityRAT-ContainerList,
    maxNrofCLI-RSSI-Resources-r16,
    maxNrofCLI-SRS-Resources-r16,
    RSSI-ResourceId-r16,
    SDT-Config-r17,
    SidelinkUEInformationNR-r16,
    SRS-PosRRC-InactiveValidityAreaPreConfigList-r18,
    SRS-ResourceId,
    SuccessPSCell-Config-r18,
    SupportedAggBandwidth-r17,
    UE-RadioPagingInfo-r17,
    UE-RadioPagingInfo-r19,
    LTM-Config-r18,
    maxNrofLTM-Configs-plus1-r18
FROM NR-RRC-Definitions;

-- TAG-NR-INTER-NODE-DEFINITIONS-STOP
-- TAG-CG-CANDIDATELIST-START

CG-CandidateList ::=                SEQUENCE {
    criticalExtensions                  CHOICE {
        c1                                  CHOICE{
            cg-CandidateList-r17                CG-CandidateList-r17-IEs,
            spare3 NULL, spare2 NULL, spare1 NULL
        },
        criticalExtensionsFuture            SEQUENCE {}
    }
}

CG-CandidateList-r17-IEs ::=        SEQUENCE {
    cg-CandidateToAddModList-r17        SEQUENCE (SIZE (1..maxNrofCondCells-r16)) OF CG-CandidateInfo-r17    OPTIONAL,
    cg-CandidateToReleaseList-r17       SEQUENCE (SIZE (1..maxNrofCondCells-r16)) OF CG-CandidateInfoId-r17  OPTIONAL,
    nonCriticalExtension                SEQUENCE {}                                                          OPTIONAL
}

CG-CandidateInfo-r17 ::=            SEQUENCE {
    cg-CandidateInfoId-r17              CG-CandidateInfoId-r17,
    candidateCG-Config-r17             OCTET STRING (CONTAINING CG-Config)
}

CG-CandidateInfoId-r17::=           SEQUENCE {
    ssbFrequency-r17                    ARFCN-ValueNR,
    physCellId-r17                      PhysCellId
}

-- TAG-CG-CANDIDATELIST-STOP
-- TAG-HANDOVER-COMMAND-START

HandoverCommand ::=                      SEQUENCE {
    criticalExtensions                       CHOICE {
        c1                                       CHOICE{
            handoverCommand                          HandoverCommand-IEs,
            spare3 NULL, spare2 NULL, spare1 NULL
        },
        criticalExtensionsFuture                 SEQUENCE {}
    }
}

HandoverCommand-IEs ::=                  SEQUENCE {
    handoverCommandMessage                   OCTET STRING (CONTAINING RRCReconfiguration),
    nonCriticalExtension                     HandoverCommand-v1800-IEs                             OPTIONAL
}

HandoverCommand-v1800-IEs ::=            SEQUENCE {
    candPSCellExecutionConditionInfo-r18     CandPSCellExecutionConditionInfo-r18                  OPTIONAL,
    nonCriticalExtension                     SEQUENCE {}                                           OPTIONAL
}

CandPSCellExecutionConditionInfo-r18 ::= SEQUENCE {
    candPSCellExecCondReportConfigNR-r18     SEQUENCE (SIZE (1..2)) OF ReportConfigNR,
    ...
}

-- TAG-HANDOVER-COMMAND-STOP
-- TAG-HANDOVER-PREPARATION-INFORMATION-START

HandoverPreparationInformation ::=      SEQUENCE {
    criticalExtensions                      CHOICE {
        c1                                      CHOICE{
            handoverPreparationInformation          HandoverPreparationInformation-IEs,
            spare3 NULL, spare2 NULL, spare1 NULL
        },
        criticalExtensionsFuture            SEQUENCE {}
    }
}

HandoverPreparationInformation-IEs ::=  SEQUENCE {
    ue-CapabilityRAT-List                   UE-CapabilityRAT-ContainerList,
    sourceConfig                            AS-Config                                       OPTIONAL, -- Cond HO
    rrm-Config                              RRM-Config                                      OPTIONAL,
    as-Context                              AS-Context                                      OPTIONAL,
    nonCriticalExtension                    SEQUENCE {}                                     OPTIONAL
}

AS-Config ::=                           SEQUENCE {
    rrcReconfiguration                      OCTET STRING (CONTAINING RRCReconfiguration),
    ...,
    [[
    sourceRB-SN-Config                      OCTET STRING (CONTAINING RadioBearerConfig)     OPTIONAL,
    sourceSCG-NR-Config                     OCTET STRING (CONTAINING RRCReconfiguration)    OPTIONAL,
    sourceSCG-EUTRA-Config                  OCTET STRING                                    OPTIONAL
    ]],
    [[
    sourceSCG-Configured                    ENUMERATED {true}                               OPTIONAL
    ]],
    [[
    sdt-Config-r17                          SDT-Config-r17                                  OPTIONAL
    ]],
    [[
    srs-PosRRC-InactiveValidityAreaPreConfigList-r18  SRS-PosRRC-InactiveValidityAreaPreConfigList-r18   OPTIONAL
    ]]
}

AS-Context ::=                          SEQUENCE {
    reestablishmentInfo                     ReestablishmentInfo                                 OPTIONAL,
    configRestrictInfo                      ConfigRestrictInfoSCG                               OPTIONAL,
    ...,
    [[  ran-NotificationAreaInfo            RAN-NotificationAreaInfo                            OPTIONAL
    ]],
    [[  ueAssistanceInformation             OCTET STRING (CONTAINING UEAssistanceInformation)   OPTIONAL   -- Cond HO2
    ]],
    [[
    selectedBandCombinationSN               BandCombinationInfoSN                               OPTIONAL
    ]],
    [[
    configRestrictInfoDAPS-r16              ConfigRestrictInfoDAPS-r16                          OPTIONAL,
    sidelinkUEInformationNR-r16             OCTET STRING                                        OPTIONAL,
    sidelinkUEInformationEUTRA-r16          OCTET STRING                                        OPTIONAL,
    ueAssistanceInformationEUTRA-r16        OCTET STRING                                        OPTIONAL,
    ueAssistanceInformationSCG-r16          OCTET STRING (CONTAINING UEAssistanceInformation)   OPTIONAL,   -- Cond HO2
    needForGapsInfoNR-r16                   NeedForGapsInfoNR-r16                               OPTIONAL
    ]],
    [[
    configRestrictInfoDAPS-v1640            ConfigRestrictInfoDAPS-v1640                        OPTIONAL
    ]],
    [[
    needForGapNCSG-InfoNR-r17               NeedForGapNCSG-InfoNR-r17                           OPTIONAL,
    needForGapNCSG-InfoEUTRA-r17            NeedForGapNCSG-InfoEUTRA-r17                        OPTIONAL,
    mbsInterestIndication-r17               OCTET STRING (CONTAINING MBSInterestIndication-r17) OPTIONAL
    ]],
    [[
    needForInterruptionInfoNR-r18           NeedForInterruptionInfoNR-r18                       OPTIONAL,
    flightPathInfoReport-r18                FlightPathInfoReport-r18                            OPTIONAL
    ]],
    [[
    retainLoggedMeasurements-r19            ENUMERATED {true}                                   OPTIONAL,
    ue-ApplicabilityReportList-r19          ApplicabilityReportList-r19                         OPTIONAL
    ]]
}

ConfigRestrictInfoDAPS-r16 ::=          SEQUENCE {
    powerCoordination-r16                   SEQUENCE {
        p-DAPS-Source-r16                       P-Max,
        p-DAPS-Target-r16                       P-Max,
        uplinkPowerSharingDAPS-Mode-r16          ENUMERATED {semi-static-mode1, semi-static-mode2, dynamic }
    }                                                                                                       OPTIONAL
}

ConfigRestrictInfoDAPS-v1640 ::=    SEQUENCE {
    sourceFeatureSetPerDownlinkCC-r16   FeatureSetDownlinkPerCC-Id,
    sourceFeatureSetPerUplinkCC-r16     FeatureSetUplinkPerCC-Id
}

ReestablishmentInfo ::=             SEQUENCE {
    sourcePhysCellId                        PhysCellId,
    targetCellShortMAC-I                    ShortMAC-I,
    additionalReestabInfoList               ReestabNCellInfoList                            OPTIONAL
}

ReestabNCellInfoList ::=             SEQUENCE ( SIZE (1..maxCellPrep) ) OF ReestabNCellInfo

ReestabNCellInfo::= SEQUENCE{
    cellIdentity                            CellIdentity,
    key-gNodeB-Star                         BIT STRING (SIZE (256)),
    shortMAC-I                              ShortMAC-I
}

RRM-Config ::=              SEQUENCE {
    ue-InactiveTime             ENUMERATED {
                                    s1, s2, s3, s5, s7, s10, s15, s20,
                                    s25, s30, s40, s50, min1, min1s20, min1s40,
                                    min2, min2s30, min3, min3s30, min4, min5, min6,
                                    min7, min8, min9, min10, min12, min14, min17, min20,
                                    min24, min28, min33, min38, min44, min50, hr1,
                                    hr1min30, hr2, hr2min30, hr3, hr3min30, hr4, hr5, hr6,
                                    hr8, hr10, hr13, hr16, hr20, day1, day1hr12, day2,
                                    day2hr12, day3, day4, day5, day7, day10, day14, day19,
                                    day24, day30, dayMoreThan30}                            OPTIONAL,
    candidateCellInfoList       MeasResultList2NR                                           OPTIONAL,
    ...,
    [[
    candidateCellInfoListSN-EUTRA      MeasResultServFreqListEUTRA-SCG                      OPTIONAL
    ]]
}

-- TAG-HANDOVER-PREPARATION-INFORMATION-STOP
-- TAG-CG-CONFIG-START

CG-Config ::=                   SEQUENCE {
    criticalExtensions                  CHOICE {
        c1                                  CHOICE{
            cg-Config                           CG-Config-IEs,
            spare3 NULL, spare2 NULL, spare1 NULL
        },
        criticalExtensionsFuture            SEQUENCE {}
    }
}

CG-Config-IEs ::=                   SEQUENCE {
    scg-CellGroupConfig                 OCTET STRING (CONTAINING RRCReconfiguration)    OPTIONAL,
    scg-RB-Config                       OCTET STRING (CONTAINING RadioBearerConfig)     OPTIONAL,
    configRestrictModReq                ConfigRestrictModReqSCG                         OPTIONAL,
    drx-InfoSCG                         DRX-Info                                        OPTIONAL,
    candidateCellInfoListSN             OCTET STRING (CONTAINING MeasResultList2NR)     OPTIONAL,
    measConfigSN                        MeasConfigSN                                    OPTIONAL,
    selectedBandCombination             BandCombinationInfoSN                           OPTIONAL,
    fr-InfoListSCG                      FR-InfoList                                     OPTIONAL,
    candidateServingFreqListNR          CandidateServingFreqListNR                      OPTIONAL,
    nonCriticalExtension                CG-Config-v1540-IEs                             OPTIONAL
}

CG-Config-v1540-IEs ::=             SEQUENCE {
    pSCellFrequency                     ARFCN-ValueNR                                   OPTIONAL,
    reportCGI-RequestNR                 SEQUENCE {
        requestedCellInfo                   SEQUENCE {
            ssbFrequency                        ARFCN-ValueNR,
            cellForWhichToReportCGI             PhysCellId
        }                                                                               OPTIONAL
    }                                                                                   OPTIONAL,
    ph-InfoSCG                          PH-TypeListSCG                                  OPTIONAL,
    nonCriticalExtension                CG-Config-v1560-IEs                             OPTIONAL
}

CG-Config-v1560-IEs ::=             SEQUENCE {
    pSCellFrequencyEUTRA                ARFCN-ValueEUTRA                                OPTIONAL,
    scg-CellGroupConfigEUTRA            OCTET STRING                                    OPTIONAL,
    candidateCellInfoListSN-EUTRA       OCTET STRING                                    OPTIONAL,
    candidateServingFreqListEUTRA       CandidateServingFreqListEUTRA                   OPTIONAL,
    needForGaps                         ENUMERATED {true}                               OPTIONAL,
    drx-ConfigSCG                       DRX-Config                                      OPTIONAL,
    reportCGI-RequestEUTRA              SEQUENCE {
        requestedCellInfoEUTRA          SEQUENCE {
            eutraFrequency                             ARFCN-ValueEUTRA,
            cellForWhichToReportCGI-EUTRA              EUTRA-PhysCellId
        }                                                                               OPTIONAL
    }                                                                                   OPTIONAL,
    nonCriticalExtension                CG-Config-v1590-IEs                             OPTIONAL
}

CG-Config-v1590-IEs ::=             SEQUENCE {
    scellFrequenciesSN-NR               SEQUENCE (SIZE (1.. maxNrofServingCells-1)) OF  ARFCN-ValueNR          OPTIONAL,
    scellFrequenciesSN-EUTRA            SEQUENCE (SIZE (1.. maxNrofServingCells-1)) OF  ARFCN-ValueEUTRA       OPTIONAL,
    nonCriticalExtension                CG-Config-v1610-IEs                                                    OPTIONAL
}

CG-Config-v1610-IEs ::=             SEQUENCE {
    drx-InfoSCG2                        DRX-Info2                                       OPTIONAL,
    nonCriticalExtension                CG-Config-v1620-IEs                             OPTIONAL
}

CG-Config-v1620-IEs ::=             SEQUENCE {
    ueAssistanceInformationSCG-r16      OCTET STRING (CONTAINING UEAssistanceInformation)  OPTIONAL,
    nonCriticalExtension                CG-Config-v1630-IEs                                OPTIONAL
}

CG-Config-v1630-IEs ::=             SEQUENCE {
    selectedToffset-r16                 T-Offset-r16                                       OPTIONAL,
    nonCriticalExtension                CG-Config-v1640-IEs                                OPTIONAL
}

CG-Config-v1640-IEs ::=             SEQUENCE {
    servCellInfoListSCG-NR-r16          ServCellInfoListSCG-NR-r16                      OPTIONAL,
    servCellInfoListSCG-EUTRA-r16       ServCellInfoListSCG-EUTRA-r16                   OPTIONAL,
    nonCriticalExtension                CG-Config-v1700-IEs                             OPTIONAL
}

CG-Config-v1700-IEs ::=             SEQUENCE {
    candidateCellInfoListCPC-r17        CandidateCellInfoListCPC-r17                    OPTIONAL,
    twoPHRModeSCG-r17                   ENUMERATED {enabled}                            OPTIONAL,
    nonCriticalExtension                CG-Config-v1730-IEs                             OPTIONAL
}

CG-Config-v1730-IEs ::=             SEQUENCE {
    fr1-Carriers-SCG-r17                INTEGER (1..32)                                 OPTIONAL,
    fr2-Carriers-SCG-r17                INTEGER (1..32)                                 OPTIONAL,
    nonCriticalExtension                CG-Config-v1800-IEs                             OPTIONAL
}

CG-Config-v1800-IEs ::=             SEQUENCE {
    candidateServingFreqRangeListNR-r18    CandidateServingFreqRangeListNR-r18             OPTIONAL,
    candidateServingFreqListNR-r18         CandidateServingFreqListNR-r16                  OPTIONAL,
    idc-TDM-AssistanceConfig-r18           ENUMERATED {enabled}                            OPTIONAL,
    candidateCellInfoListSubsequentCPC-r18 CandidateCellInfoListCPC-r17                    OPTIONAL,
    scpac-ReferenceConfigurationSCG-r18    ReferenceConfiguration-r18                      OPTIONAL,
    subsequentCPAC-Information-r18         CandidateCellInfoListCPC-r17                    OPTIONAL,
    successPSCell-Config-r18               SuccessPSCell-Config-r18                        OPTIONAL,
    nonCriticalExtension                   CG-Config-v1900-IEs                             OPTIONAL
}

CG-Config-v1900-IEs ::=             SEQUENCE {
    ltm-ReferenceConfigurationSCG-r19   ReferenceConfiguration-r18                         OPTIONAL,
    dummy                               INTEGER (1..maxNrofLTM-Configs-plus1-r18)          OPTIONAL,
    nonCriticalExtension                SEQUENCE {}                                        OPTIONAL
}

ServCellInfoListSCG-NR-r16 ::=      SEQUENCE (SIZE (1.. maxNrofServingCells)) OF  ServCellInfoXCG-NR-r16

ServCellInfoXCG-NR-r16 ::=          SEQUENCE {
    dl-FreqInfo-NR-r16                  FrequencyConfig-NR-r16                          OPTIONAL,
    ul-FreqInfo-NR-r16                  FrequencyConfig-NR-r16                          OPTIONAL, -- Cond FDD
    ...
}

FrequencyConfig-NR-r16 ::=          SEQUENCE {
    freqBandIndicatorNR-r16             FreqBandIndicatorNR,
    carrierCenterFreq-NR-r16            ARFCN-ValueNR,
    carrierBandwidth-NR-r16             INTEGER (1..maxNrofPhysicalResourceBlocks),
    subcarrierSpacing-NR-r16            SubcarrierSpacing
}

ServCellInfoListSCG-EUTRA-r16 ::=   SEQUENCE (SIZE (1.. maxNrofServingCellsEUTRA)) OF ServCellInfoXCG-EUTRA-r16

ServCellInfoXCG-EUTRA-r16 ::=       SEQUENCE {
    dl-CarrierFreq-EUTRA-r16            ARFCN-ValueEUTRA                                OPTIONAL,
    ul-CarrierFreq-EUTRA-r16            ARFCN-ValueEUTRA                                OPTIONAL, -- Cond FDD
    transmissionBandwidth-EUTRA-r16     TransmissionBandwidth-EUTRA-r16                 OPTIONAL,
    ...
}

TransmissionBandwidth-EUTRA-r16 ::= ENUMERATED {rb6, rb15, rb25, rb50, rb75, rb100}

PH-TypeListSCG ::=                  SEQUENCE (SIZE (1..maxNrofServingCells)) OF PH-InfoSCG

PH-InfoSCG ::=                      SEQUENCE {
    servCellIndex                       ServCellIndex,
    ph-Uplink                           PH-UplinkCarrierSCG,
    ph-SupplementaryUplink              PH-UplinkCarrierSCG                             OPTIONAL,
    ...,
    [[
    twoSRS-PUSCH-Repetition-r17         ENUMERATED{enabled}                             OPTIONAL
    ]],
    [[
    twoSRS-MultipanelScheme-r18         ENUMERATED{enabled}                             OPTIONAL
    ]]
}

PH-UplinkCarrierSCG ::=             SEQUENCE{
    ph-Type1or3                         ENUMERATED {type1, type3},
    ...
}

MeasConfigSN ::=                    SEQUENCE {
    measuredFrequenciesSN               SEQUENCE (SIZE (1..maxMeasFreqsSN)) OF NR-FreqInfo  OPTIONAL,
    ...
}

NR-FreqInfo ::=                     SEQUENCE {
    measuredFrequency                   ARFCN-ValueNR                                       OPTIONAL,
    ...
}

ConfigRestrictModReqSCG ::=         SEQUENCE {
    requestedBC-MRDC                    BandCombinationInfoSN                               OPTIONAL,
    requestedP-MaxFR1                   P-Max                                               OPTIONAL,
    ...,
    [[
    requestedPDCCH-BlindDetectionSCG    INTEGER (1..15)                                     OPTIONAL,
    requestedP-MaxEUTRA                 P-Max                                               OPTIONAL
    ]],
    [[
    requestedP-MaxFR2-r16               P-Max                                               OPTIONAL,
    requestedMaxInterFreqMeasIdSCG-r16  INTEGER(1..maxMeasIdentitiesMN)                     OPTIONAL,
    requestedMaxIntraFreqMeasIdSCG-r16  INTEGER(1..maxMeasIdentitiesMN)                     OPTIONAL,
    requestedToffset-r16                T-Offset-r16                                        OPTIONAL
    ]],
    [[
    reservedResourceConfigNRDC-r17      ResourceConfigNRDC-r17                              OPTIONAL
    ]],
    [[
    aggregatedBandwidthSN-r17           AggregatedBandwidthSN-r17                           OPTIONAL
    ]],
    [[
    requestedMaxLTM-CandidateIdSCG-r18  INTEGER(0..maxNrofLTM-Configs-r18)                  OPTIONAL
    ]],
    [[
    requestedL1-MeasConfigNRDC-r18      L1-MeasConfigNRDC-r18                               OPTIONAL
    ]],
    [[
    requestedLTM-ResourceConfigNRDC-r18 LTM-ResourceConfigNRDC-r18                          OPTIONAL
    ]],
    [[
    requestedInterSN-LTM-r19            ENUMERATED{true}                                    OPTIONAL
    ]]
}

BandCombinationIndex ::= INTEGER (1..maxBandComb)

BandCombinationInfoSN ::=           SEQUENCE {
    bandCombinationIndex                BandCombinationIndex,
    requestedFeatureSets                FeatureSetEntryIndex
}

FR-InfoList ::= SEQUENCE (SIZE (1..maxNrofServingCells-1)) OF FR-Info

FR-Info ::= SEQUENCE {
    servCellIndex       ServCellIndex,
    fr-Type             ENUMERATED {fr1, fr2}
}

CandidateServingFreqListNR ::= SEQUENCE (SIZE (1.. maxFreqIDC-MRDC)) OF ARFCN-ValueNR

CandidateServingFreqListEUTRA ::= SEQUENCE (SIZE (1.. maxFreqIDC-MRDC)) OF ARFCN-ValueEUTRA

T-Offset-r16 ::= ENUMERATED {ms0dot5, ms0dot75, ms1, ms1dot5, ms2, ms2dot5, ms3, spare1}

CandidateCellInfoListCPC-r17 ::= SEQUENCE (SIZE (1..maxFreq)) OF CandidateCellInfo-r17

CandidateCellInfo-r17 ::=        SEQUENCE {
    ssbFrequency-r17                 ARFCN-ValueNR,
    candidateList-r17                SEQUENCE (SIZE (1..maxNrofCondCells-r16)) OF CandidateCell-r17
}

CandidateCell-r17 ::=            SEQUENCE {
    physCellId-r17                   PhysCellId,
    condExecutionCondSCG-r17         OCTET STRING (CONTAINING CondReconfigExecCondSCG-r17)               OPTIONAL
}

AggregatedBandwidthSN-r17 ::= SEQUENCE {
    aggBW-FDD-DL-r17              SupportedAggBandwidth-r17                 OPTIONAL,
    aggBW-FDD-UL-r17              SupportedAggBandwidth-r17                 OPTIONAL,
    aggBW-TDD-DL-r17              SupportedAggBandwidth-r17                 OPTIONAL,
    aggBW-TDD-UL-r17              SupportedAggBandwidth-r17                 OPTIONAL,
    aggBW-TotalDL-r17             SupportedAggBandwidth-r17                 OPTIONAL,
    aggBW-TotalUL-r17             SupportedAggBandwidth-r17                 OPTIONAL
}

-- TAG-CG-CONFIG-STOP
-- TAG-CG-CONFIG-INFO-START

CG-ConfigInfo ::=               SEQUENCE {
    criticalExtensions              CHOICE {
        c1                              CHOICE{
            cg-ConfigInfo               CG-ConfigInfo-IEs,
            spare3 NULL, spare2 NULL, spare1 NULL
        },
        criticalExtensionsFuture        SEQUENCE {}
    }
}

CG-ConfigInfo-IEs ::=           SEQUENCE {
    ue-CapabilityInfo               OCTET STRING (CONTAINING UE-CapabilityRAT-ContainerList)          OPTIONAL,-- Cond SN-AddMod
    candidateCellInfoListMN         MeasResultList2NR                                                 OPTIONAL,
    candidateCellInfoListSN         OCTET STRING (CONTAINING MeasResultList2NR)                       OPTIONAL,
    measResultCellListSFTD-NR       MeasResultCellListSFTD-NR                                         OPTIONAL,
    scgFailureInfo                  SEQUENCE {
        failureType                     ENUMERATED { t310-Expiry, randomAccessProblem,
                                                     rlc-MaxNumRetx, synchReconfigFailure-SCG,
                                                     scg-reconfigFailure,
                                                     srb3-IntegrityFailure},
        measResultSCG                   OCTET STRING (CONTAINING MeasResultSCG-Failure)
    }                                                                                                 OPTIONAL,
    configRestrictInfo              ConfigRestrictInfoSCG                                             OPTIONAL,
    drx-InfoMCG                     DRX-Info                                                          OPTIONAL,
    measConfigMN                    MeasConfigMN                                                      OPTIONAL,
    sourceConfigSCG                 OCTET STRING (CONTAINING RRCReconfiguration)                      OPTIONAL,
    scg-RB-Config                   OCTET STRING (CONTAINING RadioBearerConfig)                       OPTIONAL,
    mcg-RB-Config                   OCTET STRING (CONTAINING RadioBearerConfig)                       OPTIONAL,
    mrdc-AssistanceInfo             MRDC-AssistanceInfo                                               OPTIONAL,
    nonCriticalExtension            CG-ConfigInfo-v1540-IEs                                           OPTIONAL
}

CG-ConfigInfo-v1540-IEs ::=     SEQUENCE {
    ph-InfoMCG                      PH-TypeListMCG                                                    OPTIONAL,
    measResultReportCGI             SEQUENCE {
        ssbFrequency                    ARFCN-ValueNR,
        cellForWhichToReportCGI         PhysCellId,
        cgi-Info                        CGI-InfoNR
    }                                                                                                 OPTIONAL,
    nonCriticalExtension            CG-ConfigInfo-v1560-IEs                                           OPTIONAL
}

CG-ConfigInfo-v1560-IEs ::=  SEQUENCE {
    candidateCellInfoListMN-EUTRA       OCTET STRING                                                  OPTIONAL,
    candidateCellInfoListSN-EUTRA       OCTET STRING                                                  OPTIONAL,
    sourceConfigSCG-EUTRA               OCTET STRING                                                  OPTIONAL,
    scgFailureInfoEUTRA                 SEQUENCE {
        failureTypeEUTRA                    ENUMERATED { t313-Expiry, randomAccessProblem,
                                                    rlc-MaxNumRetx, scg-ChangeFailure},
        measResultSCG-EUTRA                 OCTET STRING
    }                                                                                                 OPTIONAL,
    drx-ConfigMCG                       DRX-Config                                                    OPTIONAL,
    measResultReportCGI-EUTRA               SEQUENCE {
        eutraFrequency                      ARFCN-ValueEUTRA,
        cellForWhichToReportCGI-EUTRA           EUTRA-PhysCellId,
        cgi-InfoEUTRA                           CGI-InfoEUTRA
    }                                                                                                 OPTIONAL,
    measResultCellListSFTD-EUTRA        MeasResultCellListSFTD-EUTRA                                  OPTIONAL,
    fr-InfoListMCG                      FR-InfoList                                                   OPTIONAL,
    nonCriticalExtension                CG-ConfigInfo-v1570-IEs                                       OPTIONAL
}

CG-ConfigInfo-v1570-IEs ::=  SEQUENCE {
    sftdFrequencyList-NR                SFTD-FrequencyList-NR                                         OPTIONAL,
    sftdFrequencyList-EUTRA             SFTD-FrequencyList-EUTRA                                      OPTIONAL,
    nonCriticalExtension                CG-ConfigInfo-v1590-IEs                                       OPTIONAL
}

CG-ConfigInfo-v1590-IEs ::=  SEQUENCE {
    servFrequenciesMN-NR            SEQUENCE (SIZE (1.. maxNrofServingCells-1)) OF  ARFCN-ValueNR     OPTIONAL,
    nonCriticalExtension            CG-ConfigInfo-v1610-IEs                                           OPTIONAL
}

CG-ConfigInfo-v1610-IEs ::=  SEQUENCE {
    drx-InfoMCG2                 DRX-Info2                                                            OPTIONAL,
    alignedDRX-Indication        ENUMERATED {true}                                                    OPTIONAL,
    scgFailureInfo-r16                  SEQUENCE {
        failureType-r16                     ENUMERATED { scg-lbtFailure-r16, beamFailureRecoveryFailure-r16,
                                                         t312-Expiry-r16, bh-RLF-r16,
                                                         beamFailure-r17, spare3, spare2, spare1},
        measResultSCG-r16                   OCTET STRING (CONTAINING MeasResultSCG-Failure)
    }                                                                                                 OPTIONAL,
    dummy1                                  SEQUENCE {
        failureTypeEUTRA-r16                    ENUMERATED { scg-lbtFailure-r16, beamFailureRecoveryFailure-r16,
                                                         t312-Expiry-r16, spare5,
                                                                     spare4, spare3, spare2, spare1},
        measResultSCG-EUTRA-r16                 OCTET STRING
    }                                                                                                 OPTIONAL,
    sidelinkUEInformationNR-r16      OCTET STRING (CONTAINING SidelinkUEInformationNR-r16)            OPTIONAL,
    sidelinkUEInformationEUTRA-r16   OCTET STRING                                                     OPTIONAL,
    nonCriticalExtension             CG-ConfigInfo-v1620-IEs                                          OPTIONAL
}

CG-ConfigInfo-v1620-IEs ::=             SEQUENCE {
    ueAssistanceInformationSourceSCG-r16    OCTET STRING (CONTAINING UEAssistanceInformation)         OPTIONAL,
    nonCriticalExtension                    CG-ConfigInfo-v1640-IEs                                   OPTIONAL
}

CG-ConfigInfo-v1640-IEs ::=             SEQUENCE {
    servCellInfoListMCG-NR-r16              ServCellInfoListMCG-NR-r16                   OPTIONAL,
    servCellInfoListMCG-EUTRA-r16           ServCellInfoListMCG-EUTRA-r16                OPTIONAL,
    nonCriticalExtension                    CG-ConfigInfo-v1700-IEs                      OPTIONAL
}

CG-ConfigInfo-v1700-IEs ::=             SEQUENCE {
    candidateCellListCPC-r17                CandidateCellListCPC-r17                     OPTIONAL,
    twoPHRModeMCG-r17                       ENUMERATED {enabled}                         OPTIONAL,
    lowMobilityEvaluationConnectedInPCell-r17 ENUMERATED {enabled}                       OPTIONAL,
    nonCriticalExtension                    CG-ConfigInfo-v1730-IEs                      OPTIONAL
}

CG-ConfigInfo-v1730-IEs ::=             SEQUENCE {
    fr1-Carriers-MCG-r17                    INTEGER (1..32)                              OPTIONAL,
    fr2-Carriers-MCG-r17                    INTEGER (1..32)                              OPTIONAL,
    nonCriticalExtension                    CG-ConfigInfo-v1800-IEs                      OPTIONAL
}

CG-ConfigInfo-v1800-IEs ::=             SEQUENCE {
    musim-GapConfigInfo-r18                 MUSIM-GapConfig-r17                          OPTIONAL,
    musim-CapRestrictionInfo-r18            SEQUENCE {
        musim-CapRestriction-r18                MUSIM-CapRestriction-r18                 OPTIONAL,
        musim-CandidateBandList-r18             MUSIM-CandidateBandList-r18              OPTIONAL
    }                                                                                    OPTIONAL,
    scpac-ReferenceConfiguration-r18        ReferenceConfiguration-r18                   OPTIONAL,
    subsequentCPAC-Candidates-r18           CandidateCellListCPC-r17                     OPTIONAL,
    nonCriticalExtension                    CG-ConfigInfo-v1900-IEs                      OPTIONAL
}

CG-ConfigInfo-v1900-IEs ::=             SEQUENCE {
    measResultReportCGI-EUTRA-v1900         SEQUENCE {
        hsdn-Cell-r19                           ENUMERATED {true}
    }                                                                                    OPTIONAL,
    ltm-ReferenceConfigurationMCG-r19       ReferenceConfiguration-r18                   OPTIONAL,
    nonCriticalExtension                    SEQUENCE {}                                  OPTIONAL
}

ServCellInfoListMCG-NR-r16 ::=          SEQUENCE (SIZE (1.. maxNrofServingCells)) OF  ServCellInfoXCG-NR-r16

ServCellInfoListMCG-EUTRA-r16 ::=       SEQUENCE (SIZE (1.. maxNrofServingCellsEUTRA)) OF ServCellInfoXCG-EUTRA-r16

SFTD-FrequencyList-NR ::=               SEQUENCE (SIZE (1..maxCellSFTD)) OF ARFCN-ValueNR

SFTD-FrequencyList-EUTRA ::=            SEQUENCE (SIZE (1..maxCellSFTD)) OF ARFCN-ValueEUTRA

ConfigRestrictInfoSCG ::=       SEQUENCE {
    allowedBC-ListMRDC              BandCombinationInfoList                                           OPTIONAL,
    powerCoordination-FR1               SEQUENCE {
        p-maxNR-FR1                     P-Max                                                         OPTIONAL,
        p-maxEUTRA                      P-Max                                                         OPTIONAL,
        p-maxUE-FR1                     P-Max                                                         OPTIONAL
    }                                                                                                 OPTIONAL,
    servCellIndexRangeSCG           SEQUENCE {
        lowBound                        ServCellIndex,
        upBound                         ServCellIndex
    }                                                                                                 OPTIONAL,   -- Cond SN-AddMod
    maxMeasFreqsSCG                     INTEGER(1..maxMeasFreqsMN)                                    OPTIONAL,
    dummy                               INTEGER(1..maxMeasIdentitiesMN)                               OPTIONAL,
    ...,
    [[
    selectedBandEntriesMNList        SEQUENCE (SIZE (1..maxBandComb)) OF SelectedBandEntriesMN        OPTIONAL,
    pdcch-BlindDetectionSCG          INTEGER (1..15)                                                  OPTIONAL,
    maxNumberROHC-ContextSessionsSN  INTEGER(0.. 16384)                                               OPTIONAL
    ]],
    [[
    maxIntraFreqMeasIdentitiesSCG     INTEGER(1..maxMeasIdentitiesMN)                                 OPTIONAL,
    maxInterFreqMeasIdentitiesSCG     INTEGER(1..maxMeasIdentitiesMN)                                 OPTIONAL
    ]],
    [[
    p-maxNR-FR1-MCG-r16               P-Max                                                           OPTIONAL,
    powerCoordination-FR2-r16         SEQUENCE {
        p-maxNR-FR2-MCG-r16                P-Max                                                      OPTIONAL,
        p-maxNR-FR2-SCG-r16                P-Max                                                      OPTIONAL,
        p-maxUE-FR2-r16                    P-Max                                                      OPTIONAL
    }                                                                                                 OPTIONAL,
    nrdc-PC-mode-FR1-r16    ENUMERATED {semi-static-mode1, semi-static-mode2, dynamic}                OPTIONAL,
    nrdc-PC-mode-FR2-r16    ENUMERATED {semi-static-mode1, semi-static-mode2, dynamic}                OPTIONAL,
    maxMeasSRS-ResourceSCG-r16       INTEGER(0..maxNrofCLI-SRS-Resources-r16)                         OPTIONAL,
    maxMeasCLI-ResourceSCG-r16       INTEGER(0..maxNrofCLI-RSSI-Resources-r16)                        OPTIONAL,
    maxNumberEHC-ContextsSN-r16      INTEGER(0..65536)                                                OPTIONAL,
    allowedReducedConfigForOverheating-r16      OverheatingAssistance                                 OPTIONAL,
    maxToffset-r16                   T-Offset-r16                                                     OPTIONAL
    ]],
    [[
    allowedReducedConfigForOverheating-r17      OverheatingAssistance-r17                             OPTIONAL,
    maxNumberUDC-DRB-r17             INTEGER(0..2)                                                    OPTIONAL,
    maxNumberCPCCandidates-r17       INTEGER(0..maxNrofCondCells-1-r17)                               OPTIONAL
    ]],
    [[
    allowedResourceConfigNRDC-r17    ResourceConfigNRDC-r17                                           OPTIONAL
    ]],
    [[
    allowedAggregatedBandwidthSNList-r17  AllowedAggregatedBandwidthSNList-r17                        OPTIONAL
    ]],
    [[
    maxNumberLTM-CandidatesSCG-r18   INTEGER(0..maxNrofLTM-Configs-r18)                               OPTIONAL
    ]],
    [[
    allowedL1-MeasConfigNRDC-r18     L1-MeasConfigNRDC-r18                                            OPTIONAL
    ]],
    [[
    allowedLTM-ResourceConfigNRDC-r18     LTM-ResourceConfigNRDC-r18                                  OPTIONAL
    ]],
    [[
    allowedInterSN-LTM-r19           ENUMERATED{allowed}                                              OPTIONAL
    ]]
}

SelectedBandEntriesMN ::=       SEQUENCE (SIZE (1..maxSimultaneousBands)) OF BandEntryIndex

BandEntryIndex ::=              INTEGER (0.. maxNrofServingCells)

PH-TypeListMCG ::=              SEQUENCE (SIZE (1..maxNrofServingCells)) OF PH-InfoMCG

PH-InfoMCG ::=                  SEQUENCE {
    servCellIndex                       ServCellIndex,
    ph-Uplink                           PH-UplinkCarrierMCG,
    ph-SupplementaryUplink              PH-UplinkCarrierMCG                                           OPTIONAL,
    ...,
    [[
    twoSRS-PUSCH-Repetition-r17         ENUMERATED{enabled}                                           OPTIONAL
    ]],
    [[
    twoSRS-MultipanelScheme-r18         ENUMERATED{enabled}                                           OPTIONAL
    ]]
}

PH-UplinkCarrierMCG ::=         SEQUENCE{
    ph-Type1or3                         ENUMERATED {type1, type3},
    ...
}

BandCombinationInfoList ::=     SEQUENCE (SIZE (1..maxBandComb)) OF BandCombinationInfo

BandCombinationInfo ::=         SEQUENCE {
    bandCombinationIndex            BandCombinationIndex,
    allowedFeatureSetsList          SEQUENCE (SIZE (1..maxFeatureSetsPerBand)) OF FeatureSetEntryIndex
}

FeatureSetEntryIndex ::=        INTEGER (1.. maxFeatureSetsPerBand)

DRX-Info ::=                    SEQUENCE {
    drx-LongCycleStartOffset        CHOICE {
        ms10                            INTEGER(0..9),
        ms20                            INTEGER(0..19),
        ms32                            INTEGER(0..31),
        ms40                            INTEGER(0..39),
        ms60                            INTEGER(0..59),
        ms64                            INTEGER(0..63),
        ms70                            INTEGER(0..69),
        ms80                            INTEGER(0..79),
        ms128                           INTEGER(0..127),
        ms160                           INTEGER(0..159),
        ms256                           INTEGER(0..255),
        ms320                           INTEGER(0..319),
        ms512                           INTEGER(0..511),
        ms640                           INTEGER(0..639),
        ms1024                          INTEGER(0..1023),
        ms1280                          INTEGER(0..1279),
        ms2048                          INTEGER(0..2047),
        ms2560                          INTEGER(0..2559),
        ms5120                          INTEGER(0..5119),
        ms10240                         INTEGER(0..10239)
    },
    shortDRX                            SEQUENCE {
        drx-ShortCycle                      ENUMERATED  {
                                                ms2, ms3, ms4, ms5, ms6, ms7, ms8, ms10, ms14, ms16, ms20, ms30, ms32,
                                                ms35, ms40, ms64, ms80, ms128, ms160, ms256, ms320, ms512, ms640, spare9,
                                                spare8, spare7, spare6, spare5, spare4, spare3, spare2, spare1 },
        drx-ShortCycleTimer                 INTEGER (1..16)
    }                                                                                             OPTIONAL
}

DRX-Info2 ::=          SEQUENCE {
    drx-onDurationTimer    CHOICE {
                               subMilliSeconds INTEGER (1..31),
                               milliSeconds    ENUMERATED {
                                   ms1, ms2, ms3, ms4, ms5, ms6, ms8, ms10, ms20, ms30, ms40, ms50, ms60,
                                   ms80, ms100, ms200, ms300, ms400, ms500, ms600, ms800, ms1000, ms1200,
                                   ms1600, spare8, spare7, spare6, spare5, spare4, spare3, spare2, spare1 }
                           }
}

MeasConfigMN ::= SEQUENCE {
    measuredFrequenciesMN               SEQUENCE (SIZE (1..maxMeasFreqsMN)) OF NR-FreqInfo        OPTIONAL,
    measGapConfig                       SetupRelease { GapConfig }                                OPTIONAL,
    gapPurpose                          ENUMERATED {perUE, perFR1}                                OPTIONAL,
    ...,
    [[
    measGapConfigFR2                    SetupRelease { GapConfig }                                OPTIONAL
    ]],
    [[
    interFreqNoGap-r16                  ENUMERATED {true}                                         OPTIONAL
    ]]
}

MRDC-AssistanceInfo ::= SEQUENCE {
    affectedCarrierFreqCombInfoListMRDC     SEQUENCE (SIZE (1..maxNrofCombIDC)) OF AffectedCarrierFreqCombInfoMRDC,
    ...,
    [[
    overheatingAssistanceSCG-r16            OCTET STRING (CONTAINING OverheatingAssistance)       OPTIONAL
    ]],
    [[
    overheatingAssistanceSCG-FR2-2-r17      OCTET STRING (CONTAINING OverheatingAssistance-r17)   OPTIONAL
    ]],
    [[
    affectedCarrierFreqRangeCombList-r18    AffectedCarrierFreqRangeCombList-r18                  OPTIONAL,
    affectedCarrierFreqCombList-r18         AffectedCarrierFreqCombList-r16                       OPTIONAL,
    idc-TDM-Assistance-r18                  IDC-TDM-Assistance-r18                                OPTIONAL
    ]]
}

AffectedCarrierFreqCombInfoMRDC ::= SEQUENCE {
    victimSystemType                    VictimSystemType,
    interferenceDirectionMRDC           ENUMERATED {eutra-nr, nr, other, utra-nr-other, nr-other, spare3, spare2, spare1},
    affectedCarrierFreqCombMRDC         SEQUENCE    {
        affectedCarrierFreqCombEUTRA        AffectedCarrierFreqCombEUTRA                          OPTIONAL,
        affectedCarrierFreqCombNR           AffectedCarrierFreqCombNR
    }                                                                                             OPTIONAL
}

VictimSystemType ::= SEQUENCE {
    gps                         ENUMERATED {true}               OPTIONAL,
    glonass                     ENUMERATED {true}               OPTIONAL,
    bds                         ENUMERATED {true}               OPTIONAL,
    galileo                     ENUMERATED {true}               OPTIONAL,
    wlan                        ENUMERATED {true}               OPTIONAL,
    bluetooth                   ENUMERATED {true}               OPTIONAL
}

AffectedCarrierFreqCombEUTRA ::= SEQUENCE (SIZE (1..maxNrofServingCellsEUTRA)) OF ARFCN-ValueEUTRA

AffectedCarrierFreqCombNR ::= SEQUENCE (SIZE (1..maxNrofServingCells)) OF ARFCN-ValueNR

CandidateCellListCPC-r17 ::= SEQUENCE (SIZE (1..maxFreq)) OF CandidateCellCPC-r17

CandidateCellCPC-r17 ::=           SEQUENCE {
    ssbFrequency-r17                   ARFCN-ValueNR,
    candidateCellList-r17              SEQUENCE (SIZE (1..maxNrofCondCells-r16)) OF PhysCellId
}

AllowedAggregatedBandwidthSNList-r17 ::=     SEQUENCE (SIZE (1..maxBandComb)) OF AllowedAggregatedBandwidth-r17

AllowedAggregatedBandwidth-r17 ::=   SEQUENCE {
    bandCombinationIndex-r17             BandCombinationIndex,
    allowedAggBW-FDD-DL-r17              SupportedAggBandwidth-r17                 OPTIONAL,
    allowedAggBW-FDD-UL-r17              SupportedAggBandwidth-r17                 OPTIONAL,
    allowedAggBW-TDD-DL-r17              SupportedAggBandwidth-r17                 OPTIONAL,
    allowedAggBW-TDD-UL-r17              SupportedAggBandwidth-r17                 OPTIONAL,
    allowedAggBW-TotalDL-r17             SupportedAggBandwidth-r17                 OPTIONAL,
    allowedAggBW-TotalUL-r17             SupportedAggBandwidth-r17                 OPTIONAL
}

-- TAG-CG-CONFIG-INFO-STOP
-- TAG-MEASUREMENT-TIMING-CONFIGURATION-START

MeasurementTimingConfiguration ::=      SEQUENCE {
    criticalExtensions                      CHOICE {
        c1                                      CHOICE{
            measTimingConf                          MeasurementTimingConfiguration-IEs,
            spare3 NULL, spare2 NULL, spare1 NULL
        },
        criticalExtensionsFuture        SEQUENCE {}
    }
}

MeasurementTimingConfiguration-IEs ::=  SEQUENCE {
    measTiming                              MeasTimingList                                      OPTIONAL,
    nonCriticalExtension                    MeasurementTimingConfiguration-v1550-IEs            OPTIONAL
}

MeasurementTimingConfiguration-v1550-IEs ::= SEQUENCE {
    campOnFirstSSB                               BOOLEAN,
    psCellOnlyOnFirstSSB                         BOOLEAN,
    nonCriticalExtension                         MeasurementTimingConfiguration-v1610-IEs       OPTIONAL
}

MeasurementTimingConfiguration-v1610-IEs ::=  SEQUENCE {
    csi-RS-Config-r16                             SEQUENCE {
        csi-RS-SubcarrierSpacing-r16                  SubcarrierSpacing,
        csi-RS-CellMobility-r16                       CSI-RS-CellMobility,
        refSSBFreq-r16                                ARFCN-ValueNR
    },
    nonCriticalExtension                          SEQUENCE {}                                   OPTIONAL
}

MeasTimingList ::= SEQUENCE (SIZE (1..maxMeasFreqsMN)) OF MeasTiming

MeasTiming ::= SEQUENCE {
    frequencyAndTiming                      SEQUENCE {
        carrierFreq                             ARFCN-ValueNR,
        ssbSubcarrierSpacing                    SubcarrierSpacing,
        ssb-MeasurementTimingConfiguration      SSB-MTC,
        ss-RSSI-Measurement                     SS-RSSI-Measurement                             OPTIONAL
    }                                                                                           OPTIONAL,
    ...,
    [[
    ssb-ToMeasure                           SSB-ToMeasure                                       OPTIONAL,
    physCellId                              PhysCellId                                          OPTIONAL
    ]]
}

-- TAG-MEASUREMENT-TIMING-CONFIGURATION-STOP
-- TAG-UE-RADIO-PAGING-INFORMATION-START

UERadioPagingInformation ::= SEQUENCE {
    criticalExtensions                  CHOICE {
        c1                                  CHOICE{
            ueRadioPagingInformation            UERadioPagingInformation-IEs,
            spare7 NULL,
            spare6 NULL, spare5 NULL, spare4 NULL,
            spare3 NULL, spare2 NULL, spare1 NULL
        },
        criticalExtensionsFuture            SEQUENCE {}
    }
}

UERadioPagingInformation-IEs ::=    SEQUENCE {
    supportedBandListNRForPaging        SEQUENCE (SIZE (1..maxBands)) OF FreqBandIndicatorNR    OPTIONAL,
    nonCriticalExtension                UERadioPagingInformation-v15e0-IEs                      OPTIONAL
}

UERadioPagingInformation-v15e0-IEs ::= SEQUENCE {
    dl-SchedulingOffset-PDSCH-TypeA-FDD-FR1     ENUMERATED {supported}          OPTIONAL,
    dl-SchedulingOffset-PDSCH-TypeA-TDD-FR1     ENUMERATED {supported}          OPTIONAL,
    dl-SchedulingOffset-PDSCH-TypeA-TDD-FR2     ENUMERATED {supported}          OPTIONAL,
    dl-SchedulingOffset-PDSCH-TypeB-FDD-FR1     ENUMERATED {supported}          OPTIONAL,
    dl-SchedulingOffset-PDSCH-TypeB-TDD-FR1     ENUMERATED {supported}          OPTIONAL,
    dl-SchedulingOffset-PDSCH-TypeB-TDD-FR2     ENUMERATED {supported}          OPTIONAL,
    nonCriticalExtension                UERadioPagingInformation-v1700-IEs          OPTIONAL
}

UERadioPagingInformation-v1700-IEs ::= SEQUENCE {
    ue-RadioPagingInfo-r17                 OCTET STRING (CONTAINING UE-RadioPagingInfo-r17)     OPTIONAL,
    inactiveStatePO-Determination-r17      ENUMERATED {supported}                               OPTIONAL,
    numberOfRxRedCap-r17                   ENUMERATED {one, two}                                OPTIONAL,
    halfDuplexFDD-TypeA-RedCap-r17         SEQUENCE (SIZE (1..maxBands)) OF FreqBandIndicatorNR OPTIONAL,
    nonCriticalExtension                   UERadioPagingInformation-v1800-IEs                   OPTIONAL
}

UERadioPagingInformation-v1800-IEs ::= SEQUENCE {
    numberOfRxERedCap-r18                  ENUMERATED {one, two}                                OPTIONAL,
    supportOf2RxXR-r18                     ENUMERATED {supported}                               OPTIONAL,
    nonCriticalExtension                   UERadioPagingInformation-v1840-IEs                   OPTIONAL
}

UERadioPagingInformation-v1840-IEs ::= SEQUENCE {
    dl-SchedulingOffset-PDSCH-TypeA-FDD-FR2-NTN-r18    ENUMERATED {supported}                   OPTIONAL,
    dl-SchedulingOffset-PDSCH-TypeB-FDD-FR2-NTN-r18    ENUMERATED {supported}                   OPTIONAL,
    nonCriticalExtension                   UERadioPagingInformation-v1900-IEs                   OPTIONAL
}

UERadioPagingInformation-v1900-IEs ::= SEQUENCE {
    ue-RadioPagingInfo-r19                 OCTET STRING (CONTAINING UE-RadioPagingInfo-r19)        OPTIONAL,
    oneRxRedCapPerBand-r19                 SEQUENCE (SIZE (1..maxBands)) OF FreqBandIndicatorNR    OPTIONAL,
    twoRxRedCapPerBand-r19                 SEQUENCE (SIZE (1..maxBands)) OF FreqBandIndicatorNR    OPTIONAL,
    oneRxE-RedCapPerBand-r19               SEQUENCE (SIZE (1..maxBands)) OF FreqBandIndicatorNR    OPTIONAL,
    twoRxE-RedCapPerBand-r19               SEQUENCE (SIZE (1..maxBands)) OF FreqBandIndicatorNR    OPTIONAL,
    twoRxXR-PerBand-r19                    SEQUENCE (SIZE (1..maxBands)) OF FreqBandIndicatorNR    OPTIONAL,
    nesCellDTX-DRX-PerBand-r19             SEQUENCE (SIZE (1..maxBands)) OF FreqBandIndicatorNR    OPTIONAL,
    nonCriticalExtension                   SEQUENCE {}                                             OPTIONAL
}

-- TAG-UE-RADIO-PAGING-INFORMATION-STOP
-- TAG-UE-RADIO-ACCESS-CAPABILITY-INFORMATION-START

UERadioAccessCapabilityInformation ::= SEQUENCE {
    criticalExtensions                  CHOICE {
        c1                                  CHOICE{
            ueRadioAccessCapabilityInformation    UERadioAccessCapabilityInformation-IEs,
            spare7 NULL,
            spare6 NULL, spare5 NULL, spare4 NULL,
            spare3 NULL, spare2 NULL, spare1 NULL
        },
        criticalExtensionsFuture            SEQUENCE {}
    }
}

UERadioAccessCapabilityInformation-IEs ::= SEQUENCE {
    ue-RadioAccessCapabilityInfo               OCTET STRING (CONTAINING UE-CapabilityRAT-ContainerList),
    nonCriticalExtension                       SEQUENCE {}                                                   OPTIONAL
}

-- TAG-UE-RADIO-ACCESS-CAPABILITY-INFORMATION-STOP
-- TAG-L1-MEASCONFIGNRDC-START

L1-MeasConfigNRDC-r18 ::= SEQUENCE {
    maxL1-MeasNoGapSCG-r18                 INTEGER(0..maxNrofL1-MeasNoGap-r18)                               OPTIONAL,
    maxL1-MeasWithGapSCG-r18               INTEGER(0..maxNrofL1-MeasWithGap-r18)                             OPTIONAL,
    maxCellsL1-MeasNoGapSCG-r18            INTEGER(0..maxNrofCellsL1-MeasNoGap-r18)                          OPTIONAL,
    maxCellsL1-MeasWithGapSCG-r18          INTEGER(0..maxNrofCellsL1-MeasWithGap-r18)                        OPTIONAL,
    maxTotalCellsL1-MeasNoGapSCG-r18       INTEGER(0..maxNrofTotalCellsL1-MeasNoGap-r18)                     OPTIONAL,
    maxSSBsL1-MeasNoGapSCG-r18             INTEGER(0..maxNrofSSBsL1-MeasNoGap-r18)                           OPTIONAL,
    maxSSBsL1-MeasWithGapSCG-r18           INTEGER(0..maxNrofSSBsL1-MeasWithGap-r18)                         OPTIONAL,
    maxTotalSSBsL1-MeasNoGapSCG-r18        INTEGER(0..maxNrofTotalSSBsL1-MeasNoGap-r18)                      OPTIONAL,
    maxCellsSSB-L1-MeasIntraFreqSCG-r18    INTEGER(0..maxNrofL1-MeasIntraFreq-r18)                           OPTIONAL,
    maxCellsSSB-L1-MeasInterFreqSCG-r18    INTEGER(0..maxNrofL1-MeasInterFreq-r18)                           OPTIONAL,
    maxReportConfigsAperiodic-r18          INTEGER(0..maxNrofReportConfigsAperiodic-r18)                     OPTIONAL,
    maxReportConfigsPeriodic-r18           INTEGER(0..maxNrofReportConfigsPeriodic-r18)                      OPTIONAL,
    maxReportConfigsSemiPersistent-r18     INTEGER(0..maxNrofReportConfigsSemiPersistent-r18)                OPTIONAL,
    ...,
    [[
    maxSSBsL1-MeasNoGapSCGExt-r18          INTEGER(0..maxNrofSSBsL1-MeasNoGapExt-r18)                        OPTIONAL
    ]],
    [[
    maxCellsL1-CSI-RS-MeasIntraFreqSCG-r19 INTEGER(0..maxNrofL1-MeasIntraFreq-r18)                           OPTIONAL,
    maxReportConfigsAperiodicCSI-RS-r19    INTEGER(0..maxNrofReportConfigsAperiodic-r18)                     OPTIONAL,
    maxReportConfigsPeriodicCSI-RS-r19     INTEGER(0..maxNrofReportConfigsPeriodic-r18)                      OPTIONAL,
    maxReportConfigsSemiPersistentCSI-RS-r19   INTEGER(0..maxNrofReportConfigsSemiPersistent-r18)            OPTIONAL,
    maxReportConfigsAperiodicSP-CSI-RS-r19     INTEGER(0..maxNrofReportConfigsAperiodic-r18)                 OPTIONAL,
    maxReportConfigsSemiPersistentSP-CSI-RS-r19    INTEGER(0..maxNrofReportConfigsSemiPersistent-r18)        OPTIONAL,
    maxResourcesL1-MeasSCG-CSI-RS-r19      INTEGER(0..maxNrofCSI-RS-Resources-r19)                           OPTIONAL
    ]],
    [[
    maxCellsL1-CSI-RS-MeasInterFreqSCG-r19 INTEGER(0..maxNrofL1-MeasInterFreq-r18)                           OPTIONAL
    ]]
}

-- TAG-L1-MEASCONFIGNRDC-STOP
-- TAG-LTM-RESOURCECONFIGNRDC-START

LTM-ResourceConfigNRDC-r18 ::= SEQUENCE {
    maxCellsTA-Meas-r18                    INTEGER(0..maxNrofCellsTA-Meas-r18)                            OPTIONAL,
    maxConfigJointTCI-States-r18           INTEGER(0..maxNrofConfigJointTCI-States-r18)                   OPTIONAL,
    maxCellsJointTCI-r18                   INTEGER(0..maxNrofCellsTCI-r18)                                OPTIONAL,
    maxConfigDL-TCI-States-r18             INTEGER(0..maxNrofConfigDL-TCI-States-r18)                     OPTIONAL,
    maxConfigUL-TCI-States-r18             INTEGER(0..maxNrofConfigUL-TCI-States-r18)                     OPTIONAL,
    maxCellsTCI-r18                        INTEGER(0..maxNrofCellsTCI-r18)                                OPTIONAL,
    maxStoredConfigCells-r18               INTEGER(0..maxNrofStoredConfigCells-r18)                       OPTIONAL,
    maxConfigCells-r18                     INTEGER(0..maxNrofConfigCells-r18)                             OPTIONAL,
    maxActivatedJointTCI-States-r18        INTEGER(0..maxNrofActivatedJointTCI-States-r18)                OPTIONAL,
    maxActivatedDL-TCI-States-r18          INTEGER(0..maxNrofActivatedDL-TCI-States-r18)                  OPTIONAL,
    maxActivatedUL-TCI-States-r18          INTEGER(0..maxNrofActivatedUL-TCI-States-r18)                  OPTIONAL,
    ...
}

-- TAG-LTM-RSOURCECONFIGNRDC-STOP
-- TAG-RESOURCECONFIGNRDC-START

ResourceConfigNRDC-r17 ::= SEQUENCE {
    fr1-ResourceConfig-r17                   ResourceConfigPerFR-r17                               OPTIONAL,
    fr2-ResourceConfig-r17                   ResourceConfigPerFR-r17                               OPTIONAL,
    maxNumberResAcrossCC-AcrossFR-r17        INTEGER (0..256)                                      OPTIONAL,
    ...
}

ResourceConfigPerFR-r17 ::= SEQUENCE {
    bm-MaxNumberCSI-RS-Resource-r17          INTEGER (0..64)                                       OPTIONAL,
    bm-MaxNumberAperiodicCSI-RS-Resource-r17 INTEGER (0..64)                                       OPTIONAL,
    cg-MaxNumberConfigsAllCC-r17             INTEGER (0..32)                                       OPTIONAL,
    maxNumberCSI-RS-BFD-r17                  INTEGER (0..64)                                       OPTIONAL,
    maxNumberCSI-RS-SSB-CBD-r17              INTEGER (0..256)                                      OPTIONAL,
    maxNumberSSB-BFD-r17                     INTEGER (0..64)                                       OPTIONAL,
    sps-MaxNumberConfigsAllCC-r17            INTEGER (0..32)                                       OPTIONAL,
    trs-MaxConfResourceSetsAllCC-r17         INTEGER (0..256)                                      OPTIONAL,
    ...
}

-- TAG-RESOURCECONFIGNRDC-STOP
-- TAG-NR-MULTIPLICITY-AND-CONSTRAINTS-START

maxMeasFreqsMN              INTEGER ::= 32  -- Maximum number of MN-configured measurement frequencies
maxMeasFreqsSN              INTEGER ::= 32  -- Maximum number of SN-configured measurement frequencies
maxMeasIdentitiesMN         INTEGER ::= 62  -- Maximum number of measurement identities that a UE can be configured with
maxCellPrep                 INTEGER ::= 32  -- Maximum number of cells prepared for handover
maxNrofL1-MeasNoGap-r18           INTEGER ::= 8  -- Maximum number of frequencies layers for L1 measurements UE can measure without gaps
maxNrofL1-MeasWithGap-r18         INTEGER ::= 8  -- Maximum number of frequencies layers for L1 measurements UE can measure with gaps
maxNrofCellsL1-MeasNoGap-r18      INTEGER ::= 8  -- Maximum number of neighboring cells for L1 measurements UE can measure without gaps
maxNrofCellsL1-MeasWithGap-r18    INTEGER ::= 8  -- Maximum number of neighboring cells for L1 measurements UE can measure with gaps
maxNrofTotalCellsL1-MeasNoGap-r18 INTEGER ::= 24 -- Maximum total number of cell across all frequencies layers UE can measure
maxNrofSSBsL1-MeasNoGap-r18       INTEGER ::= 8  -- Maximum number of SSB resources for L1 measurements without gaps
maxNrofSSBsL1-MeasNoGapExt-r18    INTEGER ::= 24 -- Maximum number of SSB resources for L1 measurements without gaps
maxNrofSSBsL1-MeasWithGap-r18     INTEGER ::= 8  -- Maximum number of SSB resources for L1 measurements with gaps
maxNrofTotalSSBsL1-MeasNoGap-r18  INTEGER ::= 64 -- Maximum total number of SSB resources for L1 measurements without gaps
maxNrofL1-MeasIntraFreq-r18       INTEGER ::= 8  -- Maximum number of RRC configured intra-frequency LTM candidate configurations
maxNrofL1-MeasInterFreq-r18       INTEGER ::= 8  -- Maximum number of RRC configured inter-frequency LTM candidate configurations
maxNrofReportConfigsAperiodic-r18 INTEGER ::= 4  -- Maximum number of aperiodic LTM CSI report configurations
maxNrofReportConfigsPeriodic-r18  INTEGER ::= 4  -- Maximum number of periodic LTM CSI report configurations
maxNrofReportConfigsSemiPersistent-r18  INTEGER ::= 4   -- Maximum number of semi-persistent LTM CSI report configurations
maxNrofCellsTA-Meas-r18           INTEGER ::= 8    -- Maximum number of LTM candidate cells for TA acquisition
maxNrofConfigJointTCI-States-r18  INTEGER ::= 128  -- Maximum number of joint LTM DL TCI states that can be configured
maxNrofConfigDL-TCI-States-r18    INTEGER ::= 128  -- Maximum number of separate LTM DL TCI states that can be configured
maxNrofConfigUL-TCI-States-r18    INTEGER ::= 64   -- Maximum number of separate LTM UL TCI states that can be configured
maxNrofCellsTCI-r18               INTEGER ::= 8    -- Maximum number of configured joint LTM TCI state(s) across candidate cells
maxNrofStoredConfigCells-r18      INTEGER ::= 16   -- Maximum number cells which can be stored by the UE
maxNrofConfigCells-r18            INTEGER ::= 4    -- Maximum number LTM candidate configurations on which UE can fast processing
maxNrofActivatedJointTCI-States-r18  INTEGER ::= 32  -- Maximum number of joint DL TCI states that can be activated via MAC CE
maxNrofActivatedDL-TCI-States-r18 INTEGER ::= 32   -- Maximum number of separate DL TCI states that can be activated via MAC CE
maxNrofActivatedUL-TCI-States-r18 INTEGER ::= 32   -- Maximum number of separate DL TCI states that can be activated via MAC CE
maxNrofCSI-RS-Resources-r19       INTEGER ::= 64   -- Maximum number of CSI-RS resources for L1-RSRP measurements

-- TAG-NR-MULTIPLICITY-AND-CONSTRAINTS-STOP
-- TAG-NR-INTER-NODE-DEFINITIONS-END-START

END

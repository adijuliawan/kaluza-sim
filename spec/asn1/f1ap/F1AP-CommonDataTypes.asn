-- Extracted by spec/tools/docx_asn1.py 1.0 from 3GPP TS 38.473 j40 (38473-j40.zip, sha256 b3a739825ca588ef8d793032498202a20307751d6109ad603687b8858bd4d60b).
-- Do not edit: regenerate with spec/tools/docx_asn1.py. Text (c) 3GPP; see spec/INDEX.tsv for the source.

F1AP-CommonDataTypes {
itu-t (0) identified-organization (4) etsi (0) mobileDomain (0)
ngran-access (22) modules (3) f1ap (3) version1 (1) f1ap-CommonDataTypes (3) }

DEFINITIONS AUTOMATIC TAGS ::=

BEGIN

Criticality		::= ENUMERATED { reject, ignore, notify }

Presence		::= ENUMERATED { optional, conditional, mandatory }

PrivateIE-ID	::= CHOICE {
	local				INTEGER (0..65535),
	global				OBJECT IDENTIFIER
}

ProcedureCode		::= INTEGER (0..255)

ProtocolExtensionID	::= INTEGER (0..65535)

ProtocolIE-ID		::= INTEGER (0..65535)

TriggeringMessage	::= ENUMERATED { initiating-message, successful-outcome, unsuccessful-outcome }

END

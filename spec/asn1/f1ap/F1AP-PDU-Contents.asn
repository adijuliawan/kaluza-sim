-- Extracted by spec/tools/docx_asn1.py 1.0 from 3GPP TS 38.473 j40 (38473-j40.zip, sha256 b3a739825ca588ef8d793032498202a20307751d6109ad603687b8858bd4d60b).
-- Do not edit: regenerate with spec/tools/docx_asn1.py. Text (c) 3GPP; see spec/INDEX.tsv for the source.

F1AP-PDU-Contents {
itu-t (0) identified-organization (4) etsi (0) mobileDomain (0)
ngran-access (22) modules (3) f1ap (3) version1 (1) f1ap-PDU-Contents (1) }

DEFINITIONS AUTOMATIC TAGS ::=

BEGIN

-- **************************************************************
--
-- IE parameter types from other modules.
--
-- **************************************************************

IMPORTS
	AssociatedSessionID,
	BroadcastMRBs-FailedToBeModified-Item,
	BroadcastMRBs-FailedToBeSetup-Item,
	BroadcastMRBs-FailedToBeSetupMod-Item,
	BroadcastMRBs-Modified-Item,
	BroadcastMRBs-Setup-Item,
	BroadcastMRBs-SetupMod-Item,
	BroadcastMRBs-ToBeModified-Item,
	BroadcastMRBs-ToBeReleased-Item,
	BroadcastMRBs-ToBeSetup-Item,
	BroadcastMRBs-ToBeSetupMod-Item,
	Candidate-SpCell-Item,
	Cause,
	Cells-Allowed-to-be-Deactivated-List-Item,
	Cells-Failed-to-be-Activated-List-Item,
	Cells-Status-Item,
	Cells-to-be-Activated-List-Item,
	Cells-to-be-Deactivated-List-Item,
	CellULConfigured,
	CriticalityDiagnostics,
	C-RNTI,
	CUtoDURRCInformation,
	DRB-Activity-Item,
	DRBs-FailedToBeModified-Item,
	DRBs-FailedToBeSetup-Item,
	DRBs-FailedToBeSetupMod-Item,
	DRB-Notify-Item,
	DRBs-ModifiedConf-Item,
	DRBs-Modified-Item,
	DRBs-Required-ToBeModified-Item,
	DRBs-Required-ToBeReleased-Item,
	DRBs-Setup-Item,
	DRBs-SetupMod-Item,
	DRBs-ToBeModified-Item,
	DRBs-ToBeReleased-Item,
	DRBs-ToBeSetup-Item,
	DRBs-ToBeSetupMod-Item,
	DRXCycle,
	DRXConfigurationIndicator,
	DUtoCURRCInformation,
	ExecuteDuplication,
	FullConfiguration,
	GNB-CU-MBS-F1AP-ID,
	GNB-CU-UE-F1AP-ID,
	GNB-DU-MBS-F1AP-ID,
	GNB-DU-UE-F1AP-ID,
	GNB-DU-ID,
	GNB-DU-Served-Cells-Item,
	GNB-CU-Name,
	GNB-DU-Name,
	InactivityMonitoringRequest,
	InactivityMonitoringResponse,
	LowerLayerPresenceStatusChange,
	MBS-CUtoDURRCInformation,
	MBSMulticastF1UContextDescriptor,
	MBS-Session-ID,
	MBS-ServiceArea,
	MulticastF1UContextReferenceCU,
	MulticastF1UContext-ToBeSetup-Item,
	MulticastF1UContext-Setup-Item,
	MulticastF1UContext-FailedToBeSetup-Item,
	MulticastMBSSessionList,
	MulticastMRBs-ToBeSetup-Item,
	MulticastMRBs-Setup-Item,
	MulticastMRBs-FailedToBeSetup-Item,
	MulticastMRBs-ToBeSetupMod-Item,
	MulticastMRBs-ToBeModified-Item,
	MulticastMRBs-ToBeReleased-Item,
	MulticastMRBs-SetupMod-Item,
	MulticastMRBs-FailedToBeSetupMod-Item,
	MulticastMRBs-Modified-Item,
	MulticastMRBs-FailedToBeModified-Item,
	BroadcastAreaScope,
	NetworkControlledRepeaterAuthorized,
	NodeAssociatedInfoResult,
	NRCGI,
	UEContextNotRetrievable,
	Potential-SpCell-Item,
	RANSharingAssistanceInformation,
	RAT-FrequencyPriorityInformation,
	RequestedSRSTransmissionCharacteristics,
	ResourceCoordinationTransferContainer,
	RRCContainer,
	RRCContainer-RRCSetupComplete,
	RRCReconfigurationCompleteIndicator,
	SCell-ToBeRemoved-Item,
	SCell-ToBeSetup-Item,
	SCell-ToBeSetupMod-Item,
	SCell-FailedtoSetup-Item,
	SCell-FailedtoSetupMod-Item,
	SDT-Volume-Threshold,
	ServCellIndex,
	Served-Cells-To-Add-Item,
	Served-Cells-To-Delete-Item,
	Served-Cells-To-Modify-Item,
	ServingCellMO,
	SNSSAI,
	SRBID,
	SRBs-FailedToBeSetup-Item,
	SRBs-FailedToBeSetupMod-Item,
	SRBs-Required-ToBeReleased-Item,
	SRBs-ToBeReleased-Item,
	SRBs-ToBeSetup-Item,
	SRBs-ToBeSetupMod-Item,
	SRBs-Modified-Item,
	SRBs-Setup-Item,
	SRBs-SetupMod-Item,
	SupportedUETypeList,
	TimeToWait,
	TransactionID,
	TransmissionActionIndicator,
	UE-associatedLogicalF1-ConnectionItem,
	UEIdentity-List-For-Paging-Item,
	DUtoCURRCContainer,
	PagingCell-Item,
	SItype-List,
	UEIdentityIndexValue,
	GNB-CU-TNL-Association-Setup-Item,
	GNB-CU-TNL-Association-Failed-To-Setup-Item,
	GNB-CU-TNL-Association-To-Add-Item,
	GNB-CU-TNL-Association-To-Remove-Item,
	GNB-CU-TNL-Association-To-Update-Item,
	MaskedIMEISV,
	PagingDRX,
	PagingPriority,
	PagingIdentity,
	Cells-to-be-Barred-Item,
	PWSSystemInformation,
	Broadcast-To-Be-Cancelled-Item,
	Cells-Broadcast-Cancelled-Item,
	NR-CGI-List-For-Restart-Item,
	PWS-Failed-NR-CGI-Item,
	RepetitionPeriod,
	NumberofBroadcastRequest,
	Cells-To-Be-Broadcast-Item,
	Cells-Broadcast-Completed-Item,
	Cancel-all-Warning-Messages-Indicator,
	EUTRA-NR-CellResourceCoordinationReq-Container,
	EUTRA-NR-CellResourceCoordinationReqAck-Container,
	RequestType,
	PLMN-Identity,
	RLCFailureIndication,
	UplinkTxDirectCurrentListInformation,
	SULAccessIndication,
	Protected-EUTRA-Resources-Item,
	GNB-DUConfigurationQuery,
	BitRate,
	RRC-Version,
	GNBDUOverloadInformation,
	RRCDeliveryStatusRequest,
	NeedforGap,
	RRCDeliveryStatus,
	ResourceCoordinationTransferInformation,
	Dedicated-SIDelivery-NeededUE-Item,
	Associated-SCell-Item,
	IgnoreResourceCoordinationContainer,
	PagingOrigin,
	UAC-Assistance-Info,
	RANUEID,
	GNB-DU-TNL-Association-To-Remove-Item,
	NotificationInformation,
	TraceActivation,
	TraceID,
	Neighbour-Cell-Information-Item,
	AdditionalRRMPriorityIndex,
	DUCURadioInformationType,
	CUDURadioInformationType,
	Transport-Layer-Address-Info,
	BHChannels-ToBeSetup-Item,
	BHChannels-Setup-Item,
	BHChannels-FailedToBeSetup-Item,
	BHChannels-ToBeModified-Item,
	BHChannels-ToBeReleased-Item,
	BHChannels-ToBeSetupMod-Item,
	BHChannels-FailedToBeModified-Item,
	BHChannels-FailedToBeSetupMod-Item,
	BHChannels-Modified-Item,
	BHChannels-SetupMod-Item,
	BHChannels-Required-ToBeReleased-Item,
	BAPAddress,
	BH-Routing-Information-Added-List-Item,
	BH-Routing-Information-Removed-List-Item,
	Child-Nodes-List,
	Activated-Cells-to-be-Updated-List,
	UL-BH-Non-UP-Traffic-Mapping,
	IABIPv6RequestType,
	IAB-TNL-Addresses-To-Remove-Item,
	IABTNLAddress,
	IAB-Allocated-TNL-Address-Item,
	IABv4AddressesRequested,
	TrafficMappingInfo,
	UL-UP-TNL-Information-to-Update-List-Item,
	UL-UP-TNL-Address-to-Update-List-Item,
	DL-UP-TNL-Address-to-Update-List-Item,
	NRV2XServicesAuthorized,
	LTEV2XServicesAuthorized,
	NRUESidelinkAggregateMaximumBitrate,
	LTEUESidelinkAggregateMaximumBitrate,
	SLDRBs-SetupMod-Item,
	SLDRBs-ModifiedConf-Item,
	SLDRBs-FailedToBeModified-Item,
	SLDRBs-FailedToBeSetup-Item,
	SLDRBs-FailedToBeSetupMod-Item,
	SLDRBs-Modified-Item,
	SLDRBs-Required-ToBeModified-Item,
	SLDRBs-Required-ToBeReleased-Item,
	SLDRBs-Setup-Item,
	SLDRBs-ToBeModified-Item,
	SLDRBs-ToBeReleased-Item,
	SLDRBs-ToBeSetup-Item,
	SLDRBs-ToBeSetupMod-Item,
	GNBCUMeasurementID,
	GNBDUMeasurementID,
	RegistrationRequest,
	ReportCharacteristics,
	CellToReportList,
	HardwareLoadIndicator,
	CellMeasurementResultList,
	ReportingPeriodicity,
	TNLCapacityIndicator,
	RAReportList,
	RLFReportInformationList,
	ReportingRequestType,
	TimeReferenceInformation,
	ConditionalInterDUMobilityInformation,
	ConditionalIntraDUMobilityInformation,
	TargetCellList,
	MDTPLMNList,
	PrivacyIndicator,
	TransportLayerAddress,
	URI-address,
	NID,
	PosAssistance-Information,
	PosBroadcast,
	PositioningBroadcastCells,
	RoutingID,
	PosAssistanceInformationFailureList,
	PosMeasurementQuantities,
	PosMeasurementResultList,
	PosReportCharacteristics,
	TRPInformationTypeItem,
	TRPInformationItem,
	LMF-MeasurementID,
	RAN-MeasurementID,
	SDT-Termination-Request,
	SRSResourceSetID,
	SpatialRelationInfo,
	SRSResourceTrigger,
	SRSConfiguration,
	TRPList,
	E-CID-MeasurementQuantities,
	MeasurementPeriodicity,
	E-CID-MeasurementResult,
	Cell-Portion-ID,
	LMF-UE-MeasurementID,
	RAN-UE-MeasurementID,
	RelativeTime1900,
	SystemFrameNumber,
	SlotNumber,
	AbortTransmission,
	TRP-MeasurementRequestList,
	MeasurementBeamInfoRequest,
	E-CID-ReportCharacteristics,
	Extended-GNB-CU-Name,
	Extended-GNB-DU-Name,
	F1CTransferPath,
	SCGIndicator,
	SpatialRelationPerSRSResource,
	MeasurementPeriodicityExtended,
	SuccessfulHOReportInformationList,
	Coverage-Modification-Notification,
	CCO-Assistance-Information,
	CellsForSON-List,
	IABCongestionIndication,
	IABConditionalRRCMessageDeliveryIndication,
	F1CTransferPathNRDC,
	BufferSizeThresh,
	IAB-TNL-Addresses-Exception,
	BAP-Header-Rewriting-Added-List-Item,
	Re-routingEnableIndicator,
	Neighbour-Node-Cells-List,
	Serving-Cells-List,
	RBSetConfiguration,
	PDCMeasurementPeriodicity,
	PDCMeasurementQuantities,
	PDCMeasurementResult,
	PDCReportType,
	RAN-UE-PDC-MeasID,
	SCGActivationRequest,
	SCGActivationStatus,
	TRP-MeasurementUpdateList,
	PRSTRPList,
	PRSTransmissionTRPList,
	ResponseTime,
	TRP-PRS-Info-List,
	PRS-Measurement-Info-List,
	PRSConfigRequestType,
	MeasurementCharacteristicsRequestIndicator,
	MeasurementTimeOccasion,
	UEReportingInformation,
	PosContextRevIndication,
	NRRedCapUEIndication,
	NRPagingeDRXInformation,
	NRPagingeDRXInformationforRRCINACTIVE,
	QoEInformation,
	CG-SDTQueryIndication,
	CG-SDTKeptIndicator,
	CG-SDTSessionInfo,
	SDTInformation,
	FiveG-ProSeAuthorized,
	UuRLCChannelToBeSetupList,
	UuRLCChannelToBeModifiedList,
	UuRLCChannelToBeReleasedList,
	UuRLCChannelSetupList,
	UuRLCChannelFailedToBeSetupList,
	UuRLCChannelModifiedList,
	UuRLCChannelFailedToBeModifiedList,
	UuRLCChannelRequiredToBeModifiedList,
	UuRLCChannelRequiredToBeReleasedList,
	PC5RLCChannelToBeSetupList,
	PC5RLCChannelToBeModifiedList,
	PC5RLCChannelToBeReleasedList,
	PC5RLCChannelSetupList,
	PC5RLCChannelFailedToBeSetupList,
	PC5RLCChannelFailedToBeModifiedList,
	PC5RLCChannelRequiredToBeModifiedList,
	PC5RLCChannelRequiredToBeReleasedList,
	PC5RLCChannelModifiedList,
	RemoteUELocalID,
	PathSwitchConfiguration,
	SidelinkRelayConfiguration,
	PagingCause,
	PEIPSAssistanceInfo,
	UEPagingCapability,
	GNBDUUESliceMaximumBitRateList,
	MDTPollutedMeasurementIndicator,
	UE-MulticastMRBs-ConfirmedToBeModified-Item,
	UE-MulticastMRBs-RequiredToBeModified-Item,
	UE-MulticastMRBs-RequiredToBeReleased-Item,
	UE-MulticastMRBs-Setup-Item,
	UE-MulticastMRBs-Setupnew-Item,
	UE-MulticastMRBs-ToBeReleased-Item,
	UE-MulticastMRBs-ToBeSetup-Item,
	UE-MulticastMRBs-ToBeSetup-atModify-Item,
	PosMeasurementAmount,
	BAP-Header-Rewriting-Removed-List-Item,
	SLDRXCycleList,
	MDTPLMNModificationList,
	ActivationRequestType,
	PosMeasGapPreConfigList,
	PosMeasurementPeriodicityNR-AoA,
	SRSPosRRCInactiveConfig,
	SDTBearerConfigurationQueryIndication,
	SDTBearerConfigurationInfo,
	ServingCellMO-List-Item,
	ServingCellMO-encoded-in-CGC-List,
	PosSItypeList,
	DAPS-HO-Status,
	UuRLCChannelID,
	UplinkTxDirectCurrentTwoCarrierListInfo,
	SRSPosRRCInactiveQueryIndication,
	MC-PagingCell-Item,
	UlTxDirectCurrentMoreCarrierInformation,
	CPACMCGInformation,
	ExtendedUEIdentityIndexValue,
	HashedUEIdentityIndexValue,
	DedicatedSIDeliveryIndication,
	Configured-BWP-List,
	MT-SDT-Information,
	LTMInformation-Setup,
	LTMConfigurationIDMappingList,
	LTMInformation-Modify,
	LTMCells-ToBeReleased-List,
	LTMCFRAResourceConfig-List,
	LTMConfiguration,
	EarlySyncInformation-Request,
	EarlySyncInformation,
	EarlySyncCandidateCellInformation-List,
	EarlySyncServingCellInformation,
	LTMCellSwitchInformation,
	DUtoCUTAInformation-List,
	CUtoDUTAInformation-List,
	DeactivationIndication,
	RAReportIndicationList,
	SuccessfulPSCellChangeReportInformationList,
	PathAdditionInformation,
	RANTSSRequestType,
	RANTimingSynchronisationStatusInfo,
	GlobalGNB-ID,
	Activated-Cells-Mapping-List-Item,
	RRC-Terminating-IAB-Donor-Related-Info,
	NCGI-to-be-Updated-List-Item,
	Mobile-IAB-MTUserLocationInformation,
	TAI,
	IndicationMCInactiveReception,
	MulticastCU2DURRCInfo,
	MulticastDU2CURRCInfo,
	MBSMulticastSessionReceptionState,
	MulticastCU2DUCommonRRCInfo,
	NRA2XServicesAuthorized,
	LTEA2XServicesAuthorized,
	NReRedCapUEIndication,
	NRPaginglongeDRXInformationforRRCINACTIVE,
	Cells-With-SSBs-Activated-List,
	Recommended-SSBs-for-Paging-List,
	S-CPAC-Configuration,
	DLLBTFailureInformationRequest,
	DLLBTFailureInformationList,
	SLPositioning-Ranging-Service-Info,
	TimeWindowInformation-SRS-List,
	TimeWindowInformation-Measurement-List,
	SRSPosRRCInactiveValidityAreaConfig,
	SRSReservationType,
	RequestedSRSPreconfigurationCharacteristics-List,
	SRSPreconfiguration-List,
	Broadcast-MRBs-Transport-Request-Item,
	TAInformation-List,
	NonIntegerDRXCycle,
	AggregatedPosSRSResourceSetList,
	F1U-PathFailure,
	LTMResetInformation,
	MobilityInitiation,
	PLMNIndexNR,
	LTMTCIStatesConfigurationsList,
	LPWUSPSAssistanceInfo,
	FurtherExtendedUEIdentityIndexValue,
	CLI-MeasurementResult-List,
	SRS-Resource-Indication,
	FailureReportingWithoutRLFReport,
	MROForLTM-Information,
	LastVisitedLTMCells,
	OnDemand-SIB1-Cell,
	LTMSecurityInformation,
	LTMInformationSCGAdd,
	LTMInformationSCGMod,
	TARemainingInfoList,
	CSI-RSCoordinationRequestList,
	CSI-RSCoordinationResultList,
	Future-Coverage-Modification-Notification,
	Predicted-CCO-Assistance-Information,
	Neighbour-Future-Coverage-Modification-Notification,
	AreaSpecificSemiPersistentSRSPosInfo,
	LTMConfig-to-Modify-List,
	InterSNLTMMCGInformation




FROM F1AP-IEs

	PrivateIE-Container{},
	ProtocolExtensionContainer{},
	ProtocolIE-Container{},
	ProtocolIE-ContainerPair{},
	ProtocolIE-SingleContainer{},
	F1AP-PRIVATE-IES,
	F1AP-PROTOCOL-EXTENSION,
	F1AP-PROTOCOL-IES,
	F1AP-PROTOCOL-IES-PAIR

FROM F1AP-Containers

	id-AssociatedSessionID,
	id-BroadcastMRBs-FailedToBeModified-List,
	id-BroadcastMRBs-FailedToBeModified-Item,
	id-BroadcastMRBs-FailedToBeSetup-List,
	id-BroadcastMRBs-FailedToBeSetup-Item,
	id-BroadcastMRBs-FailedToBeSetupMod-List,
	id-BroadcastMRBs-FailedToBeSetupMod-Item,
	id-BroadcastMRBs-Modified-List,
	id-BroadcastMRBs-Modified-Item,
	id-BroadcastMRBs-Setup-List,
	id-BroadcastMRBs-Setup-Item,
	id-BroadcastMRBs-SetupMod-List,
	id-BroadcastMRBs-SetupMod-Item,
	id-BroadcastMRBs-ToBeModified-List,
	id-BroadcastMRBs-ToBeModified-Item,
	id-BroadcastMRBs-ToBeReleased-List,
	id-BroadcastMRBs-ToBeReleased-Item,
	id-BroadcastMRBs-ToBeSetup-List,
	id-BroadcastMRBs-ToBeSetup-Item,
	id-BroadcastMRBs-ToBeSetupMod-List,
	id-BroadcastMRBs-ToBeSetupMod-Item,
	id-Candidate-SpCell-Item,
	id-Candidate-SpCell-List,
	id-Cause,
	id-Cancel-all-Warning-Messages-Indicator,
	id-Cells-Failed-to-be-Activated-List,
	id-Cells-Failed-to-be-Activated-List-Item,
	id-Cells-Status-Item,
	id-Cells-Status-List,
	id-Cells-to-be-Activated-List,
	id-Cells-to-be-Activated-List-Item,
	id-Cells-to-be-Deactivated-List,
	id-Cells-to-be-Deactivated-List-Item,
	id-Cells-Allowed-to-be-Deactivated-List,
	id-Cells-Allowed-to-be-Deactivated-List-Item,
	id-Cells-With-SSBs-Activated-List,
	id-Recommended-SSBs-for-Paging-List,
	id-ConfirmedUEID,
	id-CriticalityDiagnostics,
	id-C-RNTI,
	id-CUtoDURRCInformation,
	id-DRB-Activity-Item,
	id-DRB-Activity-List,
	id-DRBs-FailedToBeModified-Item,
	id-DRBs-FailedToBeModified-List,
	id-DRBs-FailedToBeSetup-Item,
	id-DRBs-FailedToBeSetup-List,
	id-DRBs-FailedToBeSetupMod-Item,
	id-DRBs-FailedToBeSetupMod-List,
	id-DRBs-ModifiedConf-Item,
	id-DRBs-ModifiedConf-List,
	id-DRBs-Modified-Item,
	id-DRBs-Modified-List,
	id-DRB-Notify-Item,
	id-DRB-Notify-List,
	id-DRBs-Required-ToBeModified-Item,
	id-DRBs-Required-ToBeModified-List,
	id-DRBs-Required-ToBeReleased-Item,
	id-DRBs-Required-ToBeReleased-List,
	id-DRBs-Setup-Item,
	id-DRBs-Setup-List,
	id-DRBs-SetupMod-Item,
	id-DRBs-SetupMod-List,
	id-DRBs-ToBeModified-Item,
	id-DRBs-ToBeModified-List,
	id-DRBs-ToBeReleased-Item,
	id-DRBs-ToBeReleased-List,
	id-DRBs-ToBeSetup-Item,
	id-DRBs-ToBeSetup-List,
	id-DRBs-ToBeSetupMod-Item,
	id-DRBs-ToBeSetupMod-List,
	id-DRXCycle,
	id-DUtoCURRCInformation,
	id-ExecuteDuplication,
	id-FullConfiguration,
	id-gNB-CU-MBS-F1AP-ID,
	id-gNB-CU-UE-F1AP-ID,
	id-gNB-DU-MBS-F1AP-ID,
	id-gNB-DU-UE-F1AP-ID,
	id-gNB-DU-ID,
	id-GNB-DU-Served-Cells-Item,
	id-gNB-DU-Served-Cells-List,
	id-gNB-CU-Name,
	id-gNB-DU-Name,
	id-Extended-GNB-CU-Name,
	id-Extended-GNB-DU-Name,
	id-InactivityMonitoringRequest,
	id-InactivityMonitoringResponse,
	id-MBS-CUtoDURRCInformation,
	id-MBS-Session-ID,
	id-MBS-ServiceArea,
	id-MBSMulticastF1UContextDescriptor,
	id-MC-PagingCell-Item,
	id-MC-PagingCell-List,
	id-MulticastF1UContextReferenceCU,
	id-MulticastMBSSessionSetupList,
	id-MulticastMBSSessionRemoveList,
	id-MulticastMRBs-FailedToBeModified-List,
	id-MulticastMRBs-FailedToBeModified-Item,
	id-MulticastMRBs-FailedToBeSetup-List,
	id-MulticastMRBs-FailedToBeSetup-Item,
	id-MulticastMRBs-FailedToBeSetupMod-List,
	id-MulticastMRBs-FailedToBeSetupMod-Item,
	id-MulticastMRBs-Modified-List,
	id-MulticastMRBs-Modified-Item,
	id-MulticastMRBs-Setup-List,
	id-MulticastMRBs-Setup-Item,
	id-MulticastMRBs-SetupMod-List,
	id-MulticastMRBs-SetupMod-Item,
	id-MulticastMRBs-ToBeModified-List,
	id-MulticastMRBs-ToBeModified-Item,
	id-MulticastMRBs-ToBeReleased-List,
	id-MulticastMRBs-ToBeReleased-Item,
	id-MulticastMRBs-ToBeSetup-List,
	id-MulticastMRBs-ToBeSetup-Item,
	id-MulticastMRBs-ToBeSetupMod-List,
	id-MulticastMRBs-ToBeSetupMod-Item,
	id-MulticastF1UContext-ToBeSetup-List,
	id-MulticastF1UContext-ToBeSetup-Item,
	id-MulticastF1UContext-Setup-List,
	id-MulticastF1UContext-Setup-Item,
	id-MulticastF1UContext-FailedToBeSetup-List,
	id-MulticastF1UContext-FailedToBeSetup-Item,
	id-BroadcastAreaScope,
	id-new-gNB-CU-UE-F1AP-ID,
	id-new-gNB-DU-UE-F1AP-ID,
	id-NodeAssociatedInfoResult,
	id-oldgNB-DU-UE-F1AP-ID,
	id-PLMNAssistanceInfoForNetShar,
	id-Potential-SpCell-Item,
	id-Potential-SpCell-List,
	id-RAT-FrequencyPriorityInformation,
	id-RedirectedRRCmessage,
	id-ResetType,
	id-RequestedSRSTransmissionCharacteristics,
	id-ResourceCoordinationTransferContainer,
	id-RRCContainer,
	id-RRCContainer-RRCSetupComplete,
	id-RRCReconfigurationCompleteIndicator,
	id-SCell-FailedtoSetup-List,
	id-SCell-FailedtoSetup-Item,
	id-SCell-FailedtoSetupMod-List,
	id-SCell-FailedtoSetupMod-Item,
	id-SCell-ToBeRemoved-Item,
	id-SCell-ToBeRemoved-List,
	id-SCell-ToBeSetup-Item,
	id-SCell-ToBeSetup-List,
	id-SCell-ToBeSetupMod-Item,
	id-SCell-ToBeSetupMod-List,
	id-SDT-Termination-Request,
	id-SDT-Volume-Threshold,
	id-SelectedPLMNID,
	id-Served-Cells-To-Add-Item,
	id-Served-Cells-To-Add-List,
	id-Served-Cells-To-Delete-Item,
	id-Served-Cells-To-Delete-List,
	id-Served-Cells-To-Modify-Item,
	id-Served-Cells-To-Modify-List,
	id-ServCellIndex,
	id-ServingCellMO,
	id-SNSSAI,
	id-SpCell-ID,
	id-SpCellULConfigured,
	id-SRBID,
	id-SRBs-FailedToBeSetup-Item,
	id-SRBs-FailedToBeSetup-List,
	id-SRBs-FailedToBeSetupMod-Item,
	id-SRBs-FailedToBeSetupMod-List,
	id-SRBs-Required-ToBeReleased-Item,
	id-SRBs-Required-ToBeReleased-List,
	id-SRBs-ToBeReleased-Item,
	id-SRBs-ToBeReleased-List,
	id-SRBs-ToBeSetup-Item,
	id-SRBs-ToBeSetup-List,
	id-SRBs-ToBeSetupMod-Item,
	id-SRBs-ToBeSetupMod-List,
	id-SRBs-Modified-Item,
	id-SRBs-Modified-List,
	id-SRBs-Setup-Item,
	id-SRBs-Setup-List,
	id-SRBs-SetupMod-Item,
	id-SRBs-SetupMod-List,
	id-SupportedUETypeList,
	id-TimeToWait,
	id-TransactionID,
	id-TransmissionActionIndicator,
	id-UEContextNotRetrievable,
	id-UE-associatedLogicalF1-ConnectionItem,
	id-UE-associatedLogicalF1-ConnectionListResAck,
	id-UEIdentity-List-For-Paging-List,
	id-UEIdentity-List-For-Paging-Item,
	id-UE-MulticastMRBs-ConfirmedToBeModified-List,
	id-UE-MulticastMRBs-ConfirmedToBeModified-Item,
	id-UE-MulticastMRBs-RequiredToBeModified-List,
	id-UE-MulticastMRBs-RequiredToBeModified-Item,
	id-UE-MulticastMRBs-RequiredToBeReleased-List,
	id-UE-MulticastMRBs-RequiredToBeReleased-Item,
	id-UE-MulticastMRBs-Setup-List,
	id-UE-MulticastMRBs-Setup-Item,
	id-UE-MulticastMRBs-Setupnew-List,
	id-UE-MulticastMRBs-Setupnew-Item,
	id-UE-MulticastMRBs-ToBeReleased-List,
	id-UE-MulticastMRBs-ToBeReleased-Item,
	id-UE-MulticastMRBs-ToBeSetup-atModify-List,
	id-UE-MulticastMRBs-ToBeSetup-atModify-Item,
	id-UE-MulticastMRBs-ToBeSetup-List,
	id-UE-MulticastMRBs-ToBeSetup-Item,
	id-DUtoCURRCContainer,
	id-NRCGI,
	id-PagingCell-Item,
	id-PagingCell-List,
	id-PagingDRX,
	id-PagingPriority,
	id-SItype-List,
	id-UEIdentityIndexValue,
	id-GNB-CU-TNL-Association-Setup-List,
	id-GNB-CU-TNL-Association-Setup-Item,
	id-GNB-CU-TNL-Association-Failed-To-Setup-List,
	id-GNB-CU-TNL-Association-Failed-To-Setup-Item,
	id-GNB-CU-TNL-Association-To-Add-Item,
	id-GNB-CU-TNL-Association-To-Add-List,
	id-GNB-CU-TNL-Association-To-Remove-Item,
	id-GNB-CU-TNL-Association-To-Remove-List,
	id-GNB-CU-TNL-Association-To-Update-Item,
	id-GNB-CU-TNL-Association-To-Update-List,
	id-MaskedIMEISV,
	id-PagingIdentity,
	id-Cells-to-be-Barred-List,
	id-Cells-to-be-Barred-Item,
	id-PWSSystemInformation,
	id-RepetitionPeriod,
	id-NumberofBroadcastRequest,
	id-Cells-To-Be-Broadcast-List,
	id-Cells-To-Be-Broadcast-Item,
	id-Cells-Broadcast-Completed-List,
	id-Cells-Broadcast-Completed-Item,
	id-Broadcast-To-Be-Cancelled-List,
	id-Broadcast-To-Be-Cancelled-Item,
	id-Cells-Broadcast-Cancelled-List,
	id-Cells-Broadcast-Cancelled-Item,
	id-NR-CGI-List-For-Restart-List,
	id-NR-CGI-List-For-Restart-Item,
	id-PWS-Failed-NR-CGI-List,
	id-PWS-Failed-NR-CGI-Item,
	id-EUTRA-NR-CellResourceCoordinationReq-Container,
	id-EUTRA-NR-CellResourceCoordinationReqAck-Container,
	id-Protected-EUTRA-Resources-List,
	id-RequestType,
	id-ServingPLMN,
	id-DRXConfigurationIndicator,
	id-RLCFailureIndication,
	id-UplinkTxDirectCurrentListInformation,
	id-SULAccessIndication,
	id-Protected-EUTRA-Resources-Item,
	id-GNB-DUConfigurationQuery,
	id-GNB-DU-UE-AMBR-UL,
	id-GNB-CU-RRC-Version,
	id-GNB-DU-RRC-Version,
	id-GNBDUOverloadInformation,
	id-NeedforGap,
	id-RRCDeliveryStatusRequest,
	id-RRCDeliveryStatus,
	id-Dedicated-SIDelivery-NeededUE-List,
	id-Dedicated-SIDelivery-NeededUE-Item,
	id-ResourceCoordinationTransferInformation,
	id-Associated-SCell-List,
	id-Associated-SCell-Item,
	id-IgnoreResourceCoordinationContainer,
	id-UAC-Assistance-Info,
	id-RANUEID,
	id-PagingOrigin,
	id-GNB-DU-TNL-Association-To-Remove-Item,
	id-GNB-DU-TNL-Association-To-Remove-List,
	id-NotificationInformation,
	id-TraceActivation,
	id-TraceID,
	id-Neighbour-Cell-Information-List,
	id-Neighbour-Cell-Information-Item,
	id-AdditionalRRMPriorityIndex,
	id-DUCURadioInformationType,
	id-CUDURadioInformationType,
	id-LowerLayerPresenceStatusChange,
	id-Transport-Layer-Address-Info,
	id-BHChannels-ToBeSetup-List,
	id-BHChannels-ToBeSetup-Item,
	id-BHChannels-Setup-List,
	id-BHChannels-Setup-Item,
	id-BHChannels-ToBeModified-Item,
	id-BHChannels-ToBeModified-List,
	id-BHChannels-ToBeReleased-Item,
	id-BHChannels-ToBeReleased-List,
	id-BHChannels-ToBeSetupMod-Item,
	id-BHChannels-ToBeSetupMod-List,
	id-BHChannels-FailedToBeSetup-Item,
	id-BHChannels-FailedToBeSetup-List,
	id-BHChannels-FailedToBeModified-Item,
	id-BHChannels-FailedToBeModified-List,
	id-BHChannels-FailedToBeSetupMod-Item,
	id-BHChannels-FailedToBeSetupMod-List,
	id-BHChannels-Modified-Item,
	id-BHChannels-Modified-List,
	id-BHChannels-SetupMod-Item,
	id-BHChannels-SetupMod-List,
	id-BHChannels-Required-ToBeReleased-Item,
	id-BHChannels-Required-ToBeReleased-List,
	id-BAPAddress,
	id-ConfiguredBAPAddress,
	id-BH-Routing-Information-Added-List,
	id-BH-Routing-Information-Added-List-Item,
	id-BH-Routing-Information-Removed-List,
	id-BH-Routing-Information-Removed-List-Item,
	id-UL-BH-Non-UP-Traffic-Mapping,
	id-Child-Nodes-List,
	id-Activated-Cells-to-be-Updated-List,
	id-IABIPv6RequestType,
	id-IAB-TNL-Addresses-To-Remove-List,
	id-IAB-TNL-Addresses-To-Remove-Item,
	id-IAB-Allocated-TNL-Address-List,
	id-IAB-Allocated-TNL-Address-Item,
	id-IABv4AddressesRequested,
	id-TrafficMappingInformation,
	id-UL-UP-TNL-Information-to-Update-List,
	id-UL-UP-TNL-Information-to-Update-List-Item,
	id-UL-UP-TNL-Address-to-Update-List,
	id-UL-UP-TNL-Address-to-Update-List-Item,
	id-DL-UP-TNL-Address-to-Update-List,
	id-DL-UP-TNL-Address-to-Update-List-Item,
	id-NRV2XServicesAuthorized,
	id-LTEV2XServicesAuthorized,
	id-NRUESidelinkAggregateMaximumBitrate,
	id-LTEUESidelinkAggregateMaximumBitrate,
	id-PC5LinkAMBR,
	id-SLDRBs-FailedToBeModified-Item,
	id-SLDRBs-FailedToBeModified-List,
	id-SLDRBs-FailedToBeSetup-Item,
	id-SLDRBs-FailedToBeSetup-List,
	id-SLDRBs-Modified-Item,
	id-SLDRBs-Modified-List,
	id-SLDRBs-Required-ToBeModified-Item,
	id-SLDRBs-Required-ToBeModified-List,
	id-SLDRBs-Required-ToBeReleased-Item,
	id-SLDRBs-Required-ToBeReleased-List,
	id-SLDRBs-Setup-Item,
	id-SLDRBs-Setup-List,
	id-SLDRBs-ToBeModified-Item,
	id-SLDRBs-ToBeModified-List,
	id-SLDRBs-ToBeReleased-Item,
	id-SLDRBs-ToBeReleased-List,
	id-SLDRBs-ToBeSetup-Item,
	id-SLDRBs-ToBeSetup-List,
	id-SLDRBs-ToBeSetupMod-Item,
	id-SLDRBs-ToBeSetupMod-List,
	id-SLDRBs-SetupMod-List,
	id-SLDRBs-FailedToBeSetupMod-List,
	id-SLDRBs-SetupMod-Item,
	id-SLDRBs-FailedToBeSetupMod-Item,
	id-SLDRBs-ModifiedConf-List,
	id-SLDRBs-ModifiedConf-Item,
	id-gNBCUMeasurementID,
	id-gNBDUMeasurementID,
	id-RegistrationRequest,
	id-ReportCharacteristics,
	id-CellToReportList,
	id-CellMeasurementResultList,
	id-HardwareLoadIndicator,
	id-ReportingPeriodicity,
	id-TNLCapacityIndicator,
	id-RAReportList,
	id-RLFReportInformationList,
	id-ReportingRequestType,
	id-TimeReferenceInformation,
	id-ConditionalInterDUMobilityInformation,
	id-ConditionalIntraDUMobilityInformation,
	id-targetCellsToCancel,
	id-requestedTargetCellGlobalID,
	id-TraceCollectionEntityIPAddress,
	id-ManagementBasedMDTPLMNList,
	id-PrivacyIndicator,
	id-TraceCollectionEntityURI,
	id-ServingNID,
	id-PosAssistance-Information,
	id-PosBroadcast,
	id-PositioningBroadcastCells,
	id-RoutingID,
	id-PosAssistanceInformationFailureList,
	id-PosMeasurementQuantities,
	id-PosMeasurementResultList,
	id-PosMeasurementPeriodicity,
	id-PosReportCharacteristics,
	id-TRPInformationTypeListTRPReq,
	id-TRPInformationTypeItem,
	id-TRPInformationListTRPResp,
	id-TRPInformationItem,
	id-LMF-MeasurementID,
	id-RAN-MeasurementID,
	id-SRSType,
	id-ActivationTime,
	id-AbortTransmission,
	id-SRSConfiguration,
	id-TRPList,
	id-E-CID-MeasurementQuantities,
	id-E-CID-MeasurementPeriodicity,
	id-E-CID-MeasurementResult,
	id-Cell-Portion-ID,
	id-LMF-UE-MeasurementID,
	id-RAN-UE-MeasurementID,
	id-SFNInitialisationTime,
	id-SystemFrameNumber,
	id-SlotNumber,
	id-TRP-MeasurementRequestList,
	id-MeasurementBeamInfoRequest,
	id-E-CID-ReportCharacteristics,
	id-F1CTransferPath,
	id-SCGIndicator,
	id-SRSSpatialRelationPerSRSResource,
	id-PosMeasurementPeriodicityExtended,
	id-SuccessfulHOReportInformationList,
	id-Coverage-Modification-Notification,
	id-CCO-Assistance-Information,
	id-CellsForSON-List,
	id-IABCongestionIndication,
	id-IABConditionalRRCMessageDeliveryIndication,
	id-F1CTransferPathNRDC,
	id-BufferSizeThresh,
	id-IAB-TNL-Addresses-Exception,
	id-BAP-Header-Rewriting-Added-List,
	id-BAP-Header-Rewriting-Added-List-Item,
	id-Re-routingEnableIndicator,
	id-Neighbour-Node-Cells-List,
	id-Serving-Cells-List,
	id-MDTPollutedMeasurementIndicator,
	id-PDCMeasurementPeriodicity,
	id-PDCMeasurementQuantities,
	id-PDCMeasurementResult,
	id-PDCReportType,
	id-RAN-UE-PDC-MeasID,
	id-SCGActivationRequest,
	id-SCGActivationStatus,
	id-TRP-MeasurementUpdateList,
	id-PRSTRPList,
	id-PRSTransmissionTRPList,
	id-ResponseTime,
	id-TRP-PRS-Info-List,
	id-PRS-Measurement-Info-List,
	id-PRSConfigRequestType,
	id-MeasurementCharacteristicsRequestIndicator,
	id-MeasurementTimeOccasion,
	id-UEReportingInformation,
	id-PosContextRevIndication,
	id-NRRedCapUEIndication,
	id-RANUEPagingDRX,
	id-CNUEPagingDRX,
	id-NRPagingeDRXInformation,
	id-NRPagingeDRXInformationforRRCINACTIVE,
	id-QoEInformation,
	id-CG-SDTQueryIndication,
	id-CG-SDTKeptIndicator,
	id-CG-SDTSessionInfoOld,
	id-SDTInformation,
	id-FiveG-ProSeAuthorized,
	id-FiveG-ProSePC5LinkAMBR,
	id-FiveG-ProSeUEPC5AggregateMaximumBitrate,
	id-UuRLCChannelToBeSetupList,
	id-UuRLCChannelToBeModifiedList,
	id-UuRLCChannelToBeReleasedList,
	id-UuRLCChannelSetupList,
	id-UuRLCChannelFailedToBeSetupList,
	id-UuRLCChannelModifiedList,
	id-UuRLCChannelFailedToBeModifiedList,
	id-UuRLCChannelRequiredToBeModifiedList,
	id-UuRLCChannelRequiredToBeReleasedList,
	id-PC5RLCChannelToBeSetupList,
	id-PC5RLCChannelToBeModifiedList,
	id-PC5RLCChannelToBeReleasedList,
	id-PC5RLCChannelSetupList,
	id-PC5RLCChannelFailedToBeSetupList,
	id-PC5RLCChannelModifiedList,
	id-PC5RLCChannelFailedToBeModifiedList,
	id-PC5RLCChannelRequiredToBeModifiedList,
	id-PC5RLCChannelRequiredToBeReleasedList,
	id-SidelinkRelayConfiguration,
	id-UpdatedRemoteUELocalID,
	id-PathSwitchConfiguration,
	id-PagingCause,
	id-PEIPSAssistanceInfo,
	id-UEPagingCapability,
	id-GNBDUUESliceMaximumBitRateList,
	id-PosMeasurementAmount,
	id-BAP-Header-Rewriting-Removed-List,
	id-BAP-Header-Rewriting-Removed-List-Item,
	id-SLDRXCycleList,
	id-ManagementBasedMDTPLMNModificationList,
	id-ActivationRequestType,
	id-PosMeasGapPreConfigList,
	id-PosMeasurementPeriodicityNR-AoA,
	id-SRSPosRRCInactiveConfig,
	id-SDTBearerConfigurationQueryIndication,
	id-SDTBearerConfigurationInfo,
	id-ServingCellMO-List,
	id-ServingCellMO-List-Item,
	id-ServingCellMO-encoded-in-CGC-List,
	id-PosSItypeList,
	id-DAPS-HO-Status,
	id-SRBMappingInfo,
	id-UplinkTxDirectCurrentTwoCarrierListInfo,
	id-SRSPosRRCInactiveQueryIndication,
	id-UlTxDirectCurrentMoreCarrierInformation,
	id-CPACMCGInformation,
	id-ExtendedUEIdentityIndexValue,
	id-HashedUEIdentityIndexValue,
	id-DedicatedSIDeliveryIndication,
	id-Configured-BWP-List,
	id-NetworkControlledRepeaterAuthorized,
	id-MT-SDT-Information,
	id-LTMInformation-Setup,
	id-LTMConfigurationIDMappingList,
	id-LTMInformation-Modify,
	id-LTMCells-ToBeReleased-List,
	id-LTMConfiguration,
	id-LTMCFRAResourceConfig-List,
	id-EarlySyncInformation-Request,
	id-EarlySyncInformation,
	id-EarlySyncCandidateCellInformation-List,
	id-EarlySyncServingCellInformation,
	id-LTMCellSwitchInformation,
	id-DUtoCUTAInformation-List,
	id-CUtoDUTAInformation-List,
	id-DeactivationIndication,
	id-RAReportIndicationList,
	id-SuccessfulPSCellChangeReportInformationList,
	id-PathAdditionInformation,
	id-RANTSSRequestType,
	id-RANTimingSynchronisationStatusInfo,
	id-Target-gNB-ID,
	id-Target-gNB-IP-address,
	id-Target-SeGW-IP-address,
	id-Activated-Cells-Mapping-List,
	id-Activated-Cells-Mapping-List-Item,
	id-F1SetupOutcome,
	id-RRC-Terminating-IAB-Donor-Related-Info,
	id-RRC-Terminating-IAB-Donor-gNB-ID,
	id-NCGI-to-be-Updated-List,
	id-NCGI-to-be-Updated-List-Item,
	id-Mobile-IAB-MTUserLocationInformation,
	id-IndicationMCInactiveReception,
	id-MulticastCU2DURRCInfo,
	id-MulticastDU2CURRCInfo,
	id-MBSMulticastSessionReceptionState,
	id-MulticastCU2DUCommonRRCInfo,
	id-NRA2XServicesAuthorized,
	id-LTEA2XServicesAuthorized,
	id-NRUESidelinkAggregateMaximumBitrateForA2X,
	id-LTEUESidelinkAggregateMaximumBitrateForA2X,
	id-NReRedCapUEIndication,
	id-NRPaginglongeDRXInformationforRRCINACTIVE,
	id-Target-F1-Terminating-Donor-gNB-ID,
	id-Broadcast-MRBs-Transport-Request-List,
	id-Broadcast-MRBs-Transport-Request-Item,
	id-S-CPAC-Configuration,
	id-DLLBTFailureInformationRequest,
	id-DLLBTFailureInformationList,
	id-SLPositioning-Ranging-Service-Info,
	id-TimeWindowInformation-SRS-List,
	id-TimeWindowInformation-Measurement-List,
	id-SRSPosRRCInactiveValidityAreaConfig,
	id-SRSReservationType,
	id-RequestedSRSPreconfigurationCharacteristics-List,
	id-SRSPreconfiguration-List,
	id-SRSInformation,
	id-TAInformation-List,
	id-NonIntegerDRXCycle,
	id-AggregatedPosSRSResourceSetList,
	id-RANSharingAssistanceInformation,
	id-F1U-PathFailure,
	id-LTMResetInformation,
	id-PreconfiguredSRSInformation,
	id-MobilityInitiation,
	id-PLMNIndexNRAssistanceInfoForNetShar,
	id-LTMTCIStatesConfigurationsList,
	id-LPWUSPSAssistanceInfo,
	id-FurtherExtendedUEIdentityIndexValue,
	id-CLI-MeasurementResult-List,
	id-SRS-Resource-Indication,
	id-FailureReportingWithoutRLFReport,
	id-MROForLTM-Information,
	id-LastVisitedLTMCells,
	id-OnDemand-SIB1-Cell,
	id-LTMSecurityInformation,
	id-LTMInformationSCGAdd,
	id-LTMInformationSCGMod,
	id-TARemainingInfoList,
	id-CSI-RSCoordinationRequestList,
	id-CSI-RSCoordinationResultList,
	id-Future-Coverage-Modification-Notification,
	id-Predicted-CCO-Assistance-Information,
	id-NeighbourFutureCoverageModNotification,
	id-AreaSpecificSemiPersistentSRSPosInfo,
	id-LTMConfig-to-Modify-List,
	id-InterSNLTMMCGInformation,
	maxCellingNBDU,
	maxnoofCandidateSpCells,
	maxnoofDRBs,
	maxnoofIndividualF1ConnectionsToReset,
	maxnoofPotentialSpCells,
	maxnoofSCells,
	maxnoofSRBs,
	maxnoofPagingCells,
	maxnoofTNLAssociations,
	maxCellineNB,
	maxnoofUEIDs,
	maxnoofBHRLCChannels,
	maxnoofRoutingEntries,
	maxnoofTLAsIAB,
	maxnoofULUPTNLInformationforIAB,
	maxnoofUPTNLAddresses,
	maxnoofSLDRBs,
	maxnoofTRPInfoTypes,
	maxnoofTRPs,
	maxnoofMRBs,
	maxnoofUEIDforPaging,
	maxnoofMRBsforUE,
	maxnoofServingCellMOs




FROM F1AP-Constants;


-- **************************************************************
--
-- RESET ELEMENTARY PROCEDURE
--
-- **************************************************************

-- **************************************************************
--
-- Reset
--
-- **************************************************************

Reset ::= SEQUENCE {
	protocolIEs			ProtocolIE-Container       { {ResetIEs} },
	...
}

ResetIEs F1AP-PROTOCOL-IES ::= {
	{ ID id-TransactionID				CRITICALITY reject	TYPE TransactionID				PRESENCE mandatory	}|
	{ ID id-Cause						CRITICALITY ignore	TYPE Cause						PRESENCE mandatory	}|
	{ ID id-ResetType					CRITICALITY reject	TYPE ResetType					PRESENCE mandatory	},
	...
}

ResetType ::= CHOICE {
	f1-Interface					ResetAll,
	partOfF1-Interface				UE-associatedLogicalF1-ConnectionListRes,
	choice-extension				ProtocolIE-SingleContainer { { ResetType-ExtIEs} }
}

ResetType-ExtIEs F1AP-PROTOCOL-IES ::= {
	...
}


ResetAll ::= ENUMERATED {
	reset-all,
	...
}

UE-associatedLogicalF1-ConnectionListRes ::= SEQUENCE (SIZE(1.. maxnoofIndividualF1ConnectionsToReset)) OF ProtocolIE-SingleContainer { { UE-associatedLogicalF1-ConnectionItemRes } }

UE-associatedLogicalF1-ConnectionItemRes F1AP-PROTOCOL-IES ::= {
	{ ID id-UE-associatedLogicalF1-ConnectionItem	CRITICALITY reject	TYPE UE-associatedLogicalF1-ConnectionItem	PRESENCE mandatory},
	...
}


-- **************************************************************
--
-- Reset Acknowledge
--
-- **************************************************************

ResetAcknowledge ::= SEQUENCE {
	protocolIEs			ProtocolIE-Container       { {ResetAcknowledgeIEs} },
	...
}

ResetAcknowledgeIEs F1AP-PROTOCOL-IES ::= {
	{ ID id-TransactionID									CRITICALITY reject	TYPE TransactionID													PRESENCE mandatory	}|
	{ ID id-UE-associatedLogicalF1-ConnectionListResAck		CRITICALITY ignore	TYPE UE-associatedLogicalF1-ConnectionListResAck			PRESENCE optional	}|
	{ ID id-CriticalityDiagnostics		CRITICALITY ignore	TYPE CriticalityDiagnostics			PRESENCE optional	},
	...
}

UE-associatedLogicalF1-ConnectionListResAck ::= SEQUENCE (SIZE(1.. maxnoofIndividualF1ConnectionsToReset)) OF ProtocolIE-SingleContainer { { UE-associatedLogicalF1-ConnectionItemResAck } }

UE-associatedLogicalF1-ConnectionItemResAck F1AP-PROTOCOL-IES ::= {
	{ ID id-UE-associatedLogicalF1-ConnectionItem	CRITICALITY ignore	TYPE UE-associatedLogicalF1-ConnectionItem 	PRESENCE mandatory },
	...
}

-- **************************************************************
--
-- ERROR INDICATION ELEMENTARY PROCEDURE
--
-- **************************************************************

-- **************************************************************
--
-- Error Indication
--
-- **************************************************************

ErrorIndication ::= SEQUENCE {
	protocolIEs			ProtocolIE-Container       {{ErrorIndicationIEs}},
	...
}

ErrorIndicationIEs F1AP-PROTOCOL-IES ::= {
	{ ID id-TransactionID				CRITICALITY reject	TYPE TransactionID				PRESENCE mandatory}|
	{ ID id-gNB-CU-UE-F1AP-ID			CRITICALITY ignore	TYPE GNB-CU-UE-F1AP-ID			PRESENCE optional	}|
	{ ID id-gNB-DU-UE-F1AP-ID			CRITICALITY ignore	TYPE GNB-DU-UE-F1AP-ID			PRESENCE optional	}|
	{ ID id-Cause						CRITICALITY ignore	TYPE Cause						PRESENCE optional	}|
	{ ID id-CriticalityDiagnostics		CRITICALITY ignore	TYPE CriticalityDiagnostics		PRESENCE optional	}|
	{ ID id-gNB-CU-MBS-F1AP-ID			CRITICALITY ignore	TYPE GNB-CU-MBS-F1AP-ID			PRESENCE optional	}|
	{ ID id-gNB-DU-MBS-F1AP-ID			CRITICALITY ignore	TYPE GNB-DU-MBS-F1AP-ID			PRESENCE optional	},
	...
}

-- **************************************************************
--
-- F1 SETUP ELEMENTARY PROCEDURE
--
-- **************************************************************

-- **************************************************************
--
-- F1 Setup Request
--
-- **************************************************************

F1SetupRequest ::= SEQUENCE {
	protocolIEs			ProtocolIE-Container       { {F1SetupRequestIEs} },
	...
}

F1SetupRequestIEs F1AP-PROTOCOL-IES ::= {
	{ ID id-TransactionID					CRITICALITY reject	TYPE TransactionID						PRESENCE mandatory	}|
	{ ID id-gNB-DU-ID						CRITICALITY reject	TYPE GNB-DU-ID							PRESENCE mandatory	}|
	{ ID id-gNB-DU-Name						CRITICALITY ignore	TYPE GNB-DU-Name						PRESENCE optional	}|
	{ ID id-gNB-DU-Served-Cells-List		CRITICALITY reject	TYPE GNB-DU-Served-Cells-List			PRESENCE optional	}|
	{ ID id-GNB-DU-RRC-Version				CRITICALITY reject	TYPE RRC-Version						PRESENCE mandatory	}|
	{ ID id-Transport-Layer-Address-Info	CRITICALITY ignore	TYPE Transport-Layer-Address-Info		PRESENCE optional	}|
	{ ID id-BAPAddress						CRITICALITY ignore	TYPE BAPAddress							PRESENCE optional	}|
	{ ID id-Extended-GNB-DU-Name			CRITICALITY ignore	TYPE Extended-GNB-DU-Name				PRESENCE optional	}|
	{ ID id-RRC-Terminating-IAB-Donor-gNB-ID	CRITICALITY reject	TYPE GlobalGNB-ID					PRESENCE optional }|
	{ ID id-Mobile-IAB-MTUserLocationInformation	CRITICALITY ignore	TYPE Mobile-IAB-MTUserLocationInformation		PRESENCE optional	},
	...
}


GNB-DU-Served-Cells-List ::= SEQUENCE (SIZE(1.. maxCellingNBDU)) OF ProtocolIE-SingleContainer { { GNB-DU-Served-Cells-ItemIEs } }

GNB-DU-Served-Cells-ItemIEs F1AP-PROTOCOL-IES ::= {
	{ ID id-GNB-DU-Served-Cells-Item		CRITICALITY reject	TYPE		GNB-DU-Served-Cells-Item	PRESENCE mandatory	},
	...
}


-- **************************************************************
--
-- F1 Setup Response
--
-- **************************************************************

F1SetupResponse ::= SEQUENCE {
	protocolIEs			ProtocolIE-Container       { {F1SetupResponseIEs} },
	...
}


F1SetupResponseIEs F1AP-PROTOCOL-IES ::= {
	{ ID id-TransactionID					CRITICALITY reject	TYPE TransactionID						PRESENCE mandatory	}|
	{ ID id-gNB-CU-Name						CRITICALITY ignore	TYPE GNB-CU-Name						PRESENCE optional	}|
	{ ID id-Cells-to-be-Activated-List		CRITICALITY reject	TYPE Cells-to-be-Activated-List			PRESENCE optional	}|
	{ ID id-GNB-CU-RRC-Version				CRITICALITY reject	TYPE RRC-Version						PRESENCE mandatory	}|
	{ ID id-Transport-Layer-Address-Info	CRITICALITY ignore	TYPE Transport-Layer-Address-Info		PRESENCE optional	}|
	{ ID id-UL-BH-Non-UP-Traffic-Mapping	CRITICALITY reject	TYPE UL-BH-Non-UP-Traffic-Mapping		PRESENCE optional	}|
	{ ID id-BAPAddress						CRITICALITY ignore	TYPE BAPAddress							PRESENCE optional	}|
	{ ID id-Extended-GNB-CU-Name			CRITICALITY ignore	TYPE Extended-GNB-CU-Name				PRESENCE optional	}|
	{ ID id-NCGI-to-be-Updated-List			CRITICALITY reject	TYPE NCGI-to-be-Updated-List			PRESENCE optional	},
	...
}


Cells-to-be-Activated-List	::= SEQUENCE (SIZE(1.. maxCellingNBDU))	OF ProtocolIE-SingleContainer { { Cells-to-be-Activated-List-ItemIEs } }

Cells-to-be-Activated-List-ItemIEs	F1AP-PROTOCOL-IES::= {
	{ ID id-Cells-to-be-Activated-List-Item				CRITICALITY reject	TYPE Cells-to-be-Activated-List-Item						PRESENCE mandatory},
	...
}


NCGI-to-be-Updated-List	::= SEQUENCE (SIZE(1.. maxCellingNBDU))	OF ProtocolIE-SingleContainer { { NCGI-to-be-Updated-List-ItemIEs } }

NCGI-to-be-Updated-List-ItemIEs	F1AP-PROTOCOL-IES::= {
	{ ID id-NCGI-to-be-Updated-List-Item				CRITICALITY reject	TYPE NCGI-to-be-Updated-List-Item						PRESENCE mandatory},
	...
}


-- **************************************************************
--
-- F1 Setup Failure
--
-- **************************************************************

F1SetupFailure ::= SEQUENCE {
	protocolIEs			ProtocolIE-Container       { {F1SetupFailureIEs} },
	...
}

F1SetupFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}


-- **************************************************************
--
-- GNB-DU CONFIGURATION UPDATE ELEMENTARY PROCEDURE
--
-- **************************************************************

-- **************************************************************
--
-- GNB-DU CONFIGURATION UPDATE
--
-- **************************************************************

GNBDUConfigurationUpdate::= SEQUENCE {
	protocolIEs			ProtocolIE-Container       { {GNBDUConfigurationUpdateIEs} },
	...
}

GNBDUConfigurationUpdateIEs F1AP-PROTOCOL-IES ::= {
	{ ID id-TransactionID							CRITICALITY reject	TYPE TransactionID												PRESENCE mandatory	}|
	{ ID id-Served-Cells-To-Add-List				CRITICALITY reject	TYPE Served-Cells-To-Add-List								PRESENCE optional	}|
	{ ID id-Served-Cells-To-Modify-List				CRITICALITY reject	TYPE Served-Cells-To-Modify-List							PRESENCE optional	}|
	{ ID id-Served-Cells-To-Delete-List				CRITICALITY reject	TYPE Served-Cells-To-Delete-List							PRESENCE optional	}|
	{ ID id-Cells-Status-List						CRITICALITY reject	TYPE Cells-Status-List											PRESENCE optional	}|
	{ ID id-Dedicated-SIDelivery-NeededUE-List		CRITICALITY ignore	TYPE Dedicated-SIDelivery-NeededUE-List					PRESENCE optional	}|
	{ ID id-gNB-DU-ID								CRITICALITY reject	TYPE GNB-DU-ID													PRESENCE optional	}|
	{ ID id-GNB-DU-TNL-Association-To-Remove-List	CRITICALITY reject	TYPE GNB-DU-TNL-Association-To-Remove-List				PRESENCE optional	}|
	{ ID id-Transport-Layer-Address-Info			CRITICALITY ignore	TYPE Transport-Layer-Address-Info							PRESENCE optional	}|
	{ ID id-Coverage-Modification-Notification		CRITICALITY ignore	TYPE Coverage-Modification-Notification					PRESENCE optional	}|
	{ ID id-gNB-DU-Name								CRITICALITY ignore	TYPE GNB-DU-Name												PRESENCE optional	}|
	{ ID id-Extended-GNB-DU-Name					CRITICALITY ignore	TYPE Extended-GNB-DU-Name										PRESENCE optional	}|
	{ ID id-RRC-Terminating-IAB-Donor-Related-Info	CRITICALITY reject	TYPE RRC-Terminating-IAB-Donor-Related-Info	         PRESENCE optional }|
	{ ID id-Mobile-IAB-MTUserLocationInformation	CRITICALITY ignore	TYPE Mobile-IAB-MTUserLocationInformation	PRESENCE optional	}|
	{ ID id-Future-Coverage-Modification-Notification		CRITICALITY ignore	TYPE Future-Coverage-Modification-Notification					PRESENCE optional	},
	...
}

Served-Cells-To-Add-List		::= SEQUENCE (SIZE(1.. maxCellingNBDU))	OF ProtocolIE-SingleContainer { { Served-Cells-To-Add-ItemIEs } }
Served-Cells-To-Modify-List	::= SEQUENCE (SIZE(1.. maxCellingNBDU))	OF ProtocolIE-SingleContainer { { Served-Cells-To-Modify-ItemIEs } }
Served-Cells-To-Delete-List	::= SEQUENCE (SIZE(1.. maxCellingNBDU))	OF ProtocolIE-SingleContainer { { Served-Cells-To-Delete-ItemIEs } }
Cells-Status-List	::= SEQUENCE (SIZE(0.. maxCellingNBDU))	OF ProtocolIE-SingleContainer { { Cells-Status-ItemIEs } }

Dedicated-SIDelivery-NeededUE-List::= SEQUENCE (SIZE(1.. maxnoofUEIDs))	OF ProtocolIE-SingleContainer { { Dedicated-SIDelivery-NeededUE-ItemIEs } }

GNB-DU-TNL-Association-To-Remove-List	::= SEQUENCE (SIZE(1.. maxnoofTNLAssociations))	OF ProtocolIE-SingleContainer { { GNB-DU-TNL-Association-To-Remove-ItemIEs } }


Served-Cells-To-Add-ItemIEs F1AP-PROTOCOL-IES	::= {
	{ ID id-Served-Cells-To-Add-Item		CRITICALITY reject	TYPE	Served-Cells-To-Add-Item				PRESENCE mandatory	},
	...
}

Served-Cells-To-Modify-ItemIEs F1AP-PROTOCOL-IES	::= {
	{ ID id-Served-Cells-To-Modify-Item			CRITICALITY reject	TYPE		Served-Cells-To-Modify-Item							PRESENCE mandatory	},
	...
}

Served-Cells-To-Delete-ItemIEs F1AP-PROTOCOL-IES	::= {
	{ ID id-Served-Cells-To-Delete-Item				CRITICALITY reject	TYPE		Served-Cells-To-Delete-Item					PRESENCE mandatory	},
	...
}

Cells-Status-ItemIEs F1AP-PROTOCOL-IES	::= {
	{ ID id-Cells-Status-Item				CRITICALITY reject	TYPE		Cells-Status-Item					PRESENCE mandatory	},
	...
}

Dedicated-SIDelivery-NeededUE-ItemIEs F1AP-PROTOCOL-IES	::= {
	{ ID id-Dedicated-SIDelivery-NeededUE-Item		CRITICALITY ignore	TYPE	Dedicated-SIDelivery-NeededUE-Item				PRESENCE mandatory	},
	...
}

GNB-DU-TNL-Association-To-Remove-ItemIEs F1AP-PROTOCOL-IES	::= {
	{ ID id-GNB-DU-TNL-Association-To-Remove-Item		CRITICALITY reject	TYPE	 GNB-DU-TNL-Association-To-Remove-Item			PRESENCE mandatory	},
	...
}


-- **************************************************************
--
-- GNB-DU CONFIGURATION UPDATE ACKNOWLEDGE
--
-- **************************************************************

GNBDUConfigurationUpdateAcknowledge ::= SEQUENCE {
	protocolIEs			ProtocolIE-Container       { {GNBDUConfigurationUpdateAcknowledgeIEs} },
	...
}


GNBDUConfigurationUpdateAcknowledgeIEs F1AP-PROTOCOL-IES ::= {
	{ ID id-TransactionID						CRITICALITY reject	TYPE TransactionID								PRESENCE mandatory	}|
	{ ID id-Cells-to-be-Activated-List			CRITICALITY reject	TYPE Cells-to-be-Activated-List				PRESENCE optional	}|
	{ ID id-CriticalityDiagnostics				CRITICALITY ignore	TYPE CriticalityDiagnostics						PRESENCE optional	}|
	{ ID id-Cells-to-be-Deactivated-List		CRITICALITY reject	TYPE Cells-to-be-Deactivated-List			PRESENCE optional	}|
	{ ID id-Transport-Layer-Address-Info		CRITICALITY ignore	TYPE Transport-Layer-Address-Info			PRESENCE optional	}|
	{ ID id-UL-BH-Non-UP-Traffic-Mapping		CRITICALITY reject	TYPE UL-BH-Non-UP-Traffic-Mapping			PRESENCE optional	}|
	{ ID id-BAPAddress							CRITICALITY ignore  TYPE BAPAddress									PRESENCE optional }|
	{ ID id-CellsForSON-List					CRITICALITY ignore  TYPE CellsForSON-List							PRESENCE optional	},
	...
}

-- **************************************************************
--
-- GNB-DU CONFIGURATION UPDATE FAILURE
--
-- **************************************************************

GNBDUConfigurationUpdateFailure ::= SEQUENCE {
	protocolIEs			ProtocolIE-Container       { {GNBDUConfigurationUpdateFailureIEs} },
	...
}

GNBDUConfigurationUpdateFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}

-- **************************************************************
--
-- GNB-CU CONFIGURATION UPDATE ELEMENTARY PROCEDURE
--
-- **************************************************************

-- **************************************************************
--
-- GNB-CU CONFIGURATION UPDATE
--
-- **************************************************************

GNBCUConfigurationUpdate ::= SEQUENCE {
	protocolIEs			ProtocolIE-Container       { { GNBCUConfigurationUpdateIEs} },
	...
}

GNBCUConfigurationUpdateIEs F1AP-PROTOCOL-IES ::= {
	{ ID id-TransactionID							CRITICALITY reject	TYPE	TransactionID											PRESENCE mandatory	}|
	{ ID id-Cells-to-be-Activated-List				CRITICALITY reject	TYPE	Cells-to-be-Activated-List							PRESENCE optional	}|
	{ ID id-Cells-to-be-Deactivated-List			CRITICALITY reject	TYPE	Cells-to-be-Deactivated-List						PRESENCE optional	}|
	{ ID id-GNB-CU-TNL-Association-To-Add-List		CRITICALITY ignore	TYPE	GNB-CU-TNL-Association-To-Add-List				PRESENCE optional	}|
	{ ID id-GNB-CU-TNL-Association-To-Remove-List	CRITICALITY ignore	TYPE	GNB-CU-TNL-Association-To-Remove-List			PRESENCE optional	}|
	{ ID id-GNB-CU-TNL-Association-To-Update-List	CRITICALITY ignore	TYPE	GNB-CU-TNL-Association-To-Update-List			PRESENCE optional	}|
	{ ID id-Cells-to-be-Barred-List					CRITICALITY ignore	TYPE	Cells-to-be-Barred-List								PRESENCE optional	}|
	{ ID id-Protected-EUTRA-Resources-List			CRITICALITY reject	TYPE	Protected-EUTRA-Resources-List					PRESENCE optional	}|
	{ ID id-Neighbour-Cell-Information-List			CRITICALITY ignore	TYPE	Neighbour-Cell-Information-List					PRESENCE optional	}|
	{ ID id-Transport-Layer-Address-Info			CRITICALITY ignore	TYPE	Transport-Layer-Address-Info						PRESENCE optional	}|
	{ ID id-UL-BH-Non-UP-Traffic-Mapping			CRITICALITY reject	TYPE	UL-BH-Non-UP-Traffic-Mapping						PRESENCE optional	}|
	{ ID id-BAPAddress								CRITICALITY ignore	TYPE BAPAddress												PRESENCE optional }|
	{ ID id-CCO-Assistance-Information				CRITICALITY ignore	TYPE CCO-Assistance-Information							PRESENCE optional	}|
	{ ID id-CellsForSON-List						CRITICALITY ignore	TYPE	CellsForSON-List										PRESENCE optional }|
	{ ID id-gNB-CU-Name								CRITICALITY ignore	TYPE	GNB-CU-Name												PRESENCE optional	}|
	{ ID id-Extended-GNB-CU-Name					CRITICALITY ignore	TYPE	Extended-GNB-CU-Name									PRESENCE optional	}|
	{ ID id-Cells-Allowed-to-be-Deactivated-List			CRITICALITY ignore	TYPE	Cells-Allowed-to-be-Deactivated-List		PRESENCE optional	}|
	{ ID id-OnDemand-SIB1-Cell								CRITICALITY ignore	TYPE	OnDemand-SIB1-Cell								PRESENCE optional	}|
	{ ID id-Predicted-CCO-Assistance-Information				CRITICALITY ignore	TYPE Predicted-CCO-Assistance-Information							PRESENCE optional	}|
	{ ID id-NeighbourFutureCoverageModNotification	CRITICALITY ignore	TYPE	Neighbour-Future-Coverage-Modification-Notification		PRESENCE optional	},
	...
}

Cells-to-be-Deactivated-List	::= SEQUENCE (SIZE(1.. maxCellingNBDU))	OF ProtocolIE-SingleContainer { { Cells-to-be-Deactivated-List-ItemIEs } }
GNB-CU-TNL-Association-To-Add-List		::= SEQUENCE (SIZE(1.. maxnoofTNLAssociations))	OF ProtocolIE-SingleContainer { { GNB-CU-TNL-Association-To-Add-ItemIEs } }
GNB-CU-TNL-Association-To-Remove-List	::= SEQUENCE (SIZE(1.. maxnoofTNLAssociations))	OF ProtocolIE-SingleContainer { { GNB-CU-TNL-Association-To-Remove-ItemIEs } }
GNB-CU-TNL-Association-To-Update-List	::= SEQUENCE (SIZE(1.. maxnoofTNLAssociations))	OF ProtocolIE-SingleContainer { { GNB-CU-TNL-Association-To-Update-ItemIEs } }
Cells-to-be-Barred-List			::= SEQUENCE(SIZE(1.. maxCellingNBDU)) OF ProtocolIE-SingleContainer { { Cells-to-be-Barred-ItemIEs } }

Cells-Allowed-to-be-Deactivated-List	::= SEQUENCE (SIZE(1.. maxCellingNBDU))	OF ProtocolIE-SingleContainer { { Cells-Allowed-to-be-Deactivated-List-ItemIEs } }

Cells-Allowed-to-be-Deactivated-List-ItemIEs F1AP-PROTOCOL-IES	::= {
	{ ID id-Cells-Allowed-to-be-Deactivated-List-Item	CRITICALITY ignore	TYPE	Cells-Allowed-to-be-Deactivated-List-Item	PRESENCE mandatory },
	...
}


Cells-to-be-Deactivated-List-ItemIEs F1AP-PROTOCOL-IES	::= {
	{ ID id-Cells-to-be-Deactivated-List-Item						CRITICALITY reject	TYPE	Cells-to-be-Deactivated-List-Item					PRESENCE mandatory	},
	...
}


GNB-CU-TNL-Association-To-Add-ItemIEs F1AP-PROTOCOL-IES	::= {
	{ ID id-GNB-CU-TNL-Association-To-Add-Item		CRITICALITY ignore	TYPE	 GNB-CU-TNL-Association-To-Add-Item			PRESENCE mandatory	},
	...
}

GNB-CU-TNL-Association-To-Remove-ItemIEs F1AP-PROTOCOL-IES	::= {
	{ ID id-GNB-CU-TNL-Association-To-Remove-Item		CRITICALITY ignore	TYPE	 GNB-CU-TNL-Association-To-Remove-Item			PRESENCE mandatory	},
	...
}

GNB-CU-TNL-Association-To-Update-ItemIEs F1AP-PROTOCOL-IES	::= {
	{ ID id-GNB-CU-TNL-Association-To-Update-Item		CRITICALITY ignore	TYPE	 GNB-CU-TNL-Association-To-Update-Item			PRESENCE mandatory	},
	...
}

Cells-to-be-Barred-ItemIEs F1AP-PROTOCOL-IES	::= {
	{ ID id-Cells-to-be-Barred-Item		CRITICALITY ignore	TYPE	 Cells-to-be-Barred-Item				PRESENCE mandatory	},
	...
}

Protected-EUTRA-Resources-List ::= SEQUENCE (SIZE(1.. maxCellineNB))	OF ProtocolIE-SingleContainer { { Protected-EUTRA-Resources-ItemIEs } }
Protected-EUTRA-Resources-ItemIEs F1AP-PROTOCOL-IES	::= {
	{ ID id-Protected-EUTRA-Resources-Item 					CRITICALITY reject 	TYPE Protected-EUTRA-Resources-Item							PRESENCE mandatory},
	...
}

Neighbour-Cell-Information-List ::= SEQUENCE (SIZE(1.. maxCellingNBDU))	OF ProtocolIE-SingleContainer { { Neighbour-Cell-Information-ItemIEs } }
Neighbour-Cell-Information-ItemIEs F1AP-PROTOCOL-IES	::= {
	{ ID id-Neighbour-Cell-Information-Item 					CRITICALITY ignore 	TYPE Neighbour-Cell-Information-Item							PRESENCE mandatory},
	...
}

-- **************************************************************
--
-- GNB-CU CONFIGURATION UPDATE ACKNOWLEDGE
--
-- **************************************************************

GNBCUConfigurationUpdateAcknowledge ::= SEQUENCE {
	protocolIEs			ProtocolIE-Container       { { GNBCUConfigurationUpdateAcknowledgeIEs} },
	...
}


GNBCUConfigurationUpdateAcknowledgeIEs F1AP-PROTOCOL-IES ::= {
	{ ID id-TransactionID								CRITICALITY reject	TYPE TransactionID											PRESENCE mandatory	}|
	{ ID id-Cells-Failed-to-be-Activated-List			CRITICALITY reject	TYPE Cells-Failed-to-be-Activated-List				PRESENCE optional}|
	{ ID id-CriticalityDiagnostics							CRITICALITY ignore	TYPE CriticalityDiagnostics								PRESENCE optional	}|
	{ ID id-GNB-CU-TNL-Association-Setup-List			CRITICALITY ignore	TYPE GNB-CU-TNL-Association-Setup-List				PRESENCE optional	}|
	{ ID id-GNB-CU-TNL-Association-Failed-To-Setup-List	CRITICALITY ignore	TYPE GNB-CU-TNL-Association-Failed-To-Setup-List	PRESENCE optional	}|
	{ ID id-Dedicated-SIDelivery-NeededUE-List				CRITICALITY ignore	TYPE Dedicated-SIDelivery-NeededUE-List				PRESENCE optional	}|
	{ ID id-Transport-Layer-Address-Info				CRITICALITY ignore	TYPE Transport-Layer-Address-Info						PRESENCE optional	}|
	{ ID id-Cells-With-SSBs-Activated-List				CRITICALITY ignore	TYPE Cells-With-SSBs-Activated-List					PRESENCE optional	},
	...
}

Cells-Failed-to-be-Activated-List	::= SEQUENCE (SIZE(1.. maxCellingNBDU))	OF ProtocolIE-SingleContainer { { Cells-Failed-to-be-Activated-List-ItemIEs } }
GNB-CU-TNL-Association-Setup-List ::= SEQUENCE (SIZE(1.. maxnoofTNLAssociations))	OF ProtocolIE-SingleContainer { { GNB-CU-TNL-Association-Setup-ItemIEs } }
GNB-CU-TNL-Association-Failed-To-Setup-List ::= SEQUENCE (SIZE(1.. maxnoofTNLAssociations))	OF ProtocolIE-SingleContainer { { GNB-CU-TNL-Association-Failed-To-Setup-ItemIEs } }

Cells-Failed-to-be-Activated-List-ItemIEs F1AP-PROTOCOL-IES		::= {
	{ ID id-Cells-Failed-to-be-Activated-List-Item		CRITICALITY reject	TYPE Cells-Failed-to-be-Activated-List-Item		PRESENCE mandatory	},
	...
}

GNB-CU-TNL-Association-Setup-ItemIEs F1AP-PROTOCOL-IES	::= {
	{ ID id-GNB-CU-TNL-Association-Setup-Item		CRITICALITY ignore	TYPE	 GNB-CU-TNL-Association-Setup-Item			PRESENCE mandatory	},
	...
}


GNB-CU-TNL-Association-Failed-To-Setup-ItemIEs F1AP-PROTOCOL-IES	::= {
	{ ID id-GNB-CU-TNL-Association-Failed-To-Setup-Item		CRITICALITY ignore	TYPE	 GNB-CU-TNL-Association-Failed-To-Setup-Item			PRESENCE mandatory	},
	...
}



-- **************************************************************
--
-- GNB-CU CONFIGURATION UPDATE FAILURE
--
-- **************************************************************

GNBCUConfigurationUpdateFailure ::= SEQUENCE {
	protocolIEs			ProtocolIE-Container       { { GNBCUConfigurationUpdateFailureIEs} },
	...
}

GNBCUConfigurationUpdateFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}


-- **************************************************************
--
-- GNB-DU RESOURCE COORDINATION REQUEST
--
-- **************************************************************

GNBDUResourceCoordinationRequest ::= SEQUENCE {
	protocolIEs		ProtocolIE-Container		{{GNBDUResourceCoordinationRequest-IEs}},
	...
}

GNBDUResourceCoordinationRequest-IEs F1AP-PROTOCOL-IES ::= {
	{ ID id-TransactionID									CRITICALITY reject	TYPE TransactionID									PRESENCE mandatory	}|
	{ ID id-RequestType										CRITICALITY reject	TYPE RequestType										PRESENCE mandatory	}|
	{ ID id-EUTRA-NR-CellResourceCoordinationReq-Container	CRITICALITY reject	TYPE EUTRA-NR-CellResourceCoordinationReq-Container	PRESENCE mandatory}|
	{ ID id-IgnoreResourceCoordinationContainer				CRITICALITY reject	TYPE IgnoreResourceCoordinationContainer		PRESENCE optional },
	...
}


-- **************************************************************
--
-- GNB-DU RESOURCE COORDINATION RESPONSE
--
-- **************************************************************

GNBDUResourceCoordinationResponse ::= SEQUENCE {
	protocolIEs		ProtocolIE-Container		{{GNBDUResourceCoordinationResponse-IEs}},
	...
}

GNBDUResourceCoordinationResponse-IEs F1AP-PROTOCOL-IES ::= {
	{ ID id-TransactionID										CRITICALITY reject	TYPE TransactionID						PRESENCE mandatory	}|
	{ ID id-EUTRA-NR-CellResourceCoordinationReqAck-Container	CRITICALITY reject	TYPE EUTRA-NR-CellResourceCoordinationReqAck-Container		PRESENCE mandatory},
	...
}

-- **************************************************************
--
-- UE Context Setup ELEMENTARY PROCEDURE
--
-- **************************************************************

-- **************************************************************
--
-- UE CONTEXT SETUP REQUEST
--
-- **************************************************************

UEContextSetupRequest ::= SEQUENCE {
	protocolIEs			ProtocolIE-Container       { { UEContextSetupRequestIEs} },
	...
}

UEContextSetupRequestIEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY ignore	TYPE GNB-DU-UE-F1AP-ID									PRESENCE optional 	}|
	{ ID id-SpCell-ID								CRITICALITY reject	TYPE NRCGI												PRESENCE mandatory	}|
	{ ID id-ServCellIndex							CRITICALITY reject	TYPE ServCellIndex										PRESENCE mandatory	}|
	{ ID id-SpCellULConfigured						CRITICALITY ignore	TYPE CellULConfigured									PRESENCE optional	}|
	{ ID id-CUtoDURRCInformation					CRITICALITY reject	TYPE CUtoDURRCInformation								PRESENCE mandatory}|
	{ ID id-Candidate-SpCell-List					CRITICALITY ignore	TYPE Candidate-SpCell-List							PRESENCE optional	}|
	{ ID id-DRXCycle								CRITICALITY ignore	TYPE DRXCycle											PRESENCE optional	}|
	{ ID id-ResourceCoordinationTransferContainer	CRITICALITY ignore	TYPE ResourceCoordinationTransferContainer		PRESENCE optional	}|
	{ ID id-SCell-ToBeSetup-List					CRITICALITY ignore	TYPE SCell-ToBeSetup-List								PRESENCE optional	}|
	{ ID id-SRBs-ToBeSetup-List						CRITICALITY reject	TYPE SRBs-ToBeSetup-List								PRESENCE optional	}|
	{ ID id-DRBs-ToBeSetup-List						CRITICALITY reject	TYPE DRBs-ToBeSetup-List								PRESENCE optional	}|
	{ ID id-InactivityMonitoringRequest				CRITICALITY reject	TYPE InactivityMonitoringRequest					PRESENCE optional	}|
	{ ID id-RAT-FrequencyPriorityInformation		CRITICALITY reject	TYPE RAT-FrequencyPriorityInformation				PRESENCE optional	}|
	{ ID id-RRCContainer							CRITICALITY ignore	TYPE RRCContainer										PRESENCE optional	}|
	{ ID id-MaskedIMEISV							CRITICALITY ignore	TYPE MaskedIMEISV										PRESENCE optional	}|
	{ ID id-ServingPLMN								CRITICALITY ignore	TYPE PLMN-Identity										PRESENCE optional	}|
	{ ID id-GNB-DU-UE-AMBR-UL						CRITICALITY ignore	TYPE BitRate											PRESENCE conditional }|
	-- The above IE shall be present only if the DRB to Be Setup List IE is present.
	{ ID id-RRCDeliveryStatusRequest				CRITICALITY ignore	TYPE RRCDeliveryStatusRequest						PRESENCE optional }|
	{ ID id-ResourceCoordinationTransferInformation	CRITICALITY ignore	TYPE ResourceCoordinationTransferInformation	PRESENCE optional	}|
	{ ID id-ServingCellMO							CRITICALITY ignore	TYPE ServingCellMO										PRESENCE optional	}|
	{ ID id-new-gNB-CU-UE-F1AP-ID					CRITICALITY reject	TYPE GNB-DU-UE-F1AP-ID									PRESENCE optional }|
	{ ID id-RANUEID									CRITICALITY ignore	TYPE RANUEID											PRESENCE optional	}|
	{ ID id-TraceActivation							CRITICALITY ignore	TYPE TraceActivation									PRESENCE optional	}|
	{ ID id-AdditionalRRMPriorityIndex				CRITICALITY ignore	TYPE AdditionalRRMPriorityIndex						PRESENCE optional }|
	{ ID id-BHChannels-ToBeSetup-List				CRITICALITY reject	TYPE BHChannels-ToBeSetup-List						PRESENCE optional	}|
	{ ID id-ConfiguredBAPAddress					CRITICALITY reject	TYPE BAPAddress											PRESENCE optional	}|
	{ ID id-NRV2XServicesAuthorized					CRITICALITY ignore	TYPE NRV2XServicesAuthorized							PRESENCE optional }|
	{ ID id-LTEV2XServicesAuthorized				CRITICALITY ignore	TYPE LTEV2XServicesAuthorized						PRESENCE optional }|
	{ ID id-NRUESidelinkAggregateMaximumBitrate		CRITICALITY ignore	TYPE NRUESidelinkAggregateMaximumBitrate			PRESENCE optional }|
	{ ID id-LTEUESidelinkAggregateMaximumBitrate	CRITICALITY ignore	TYPE LTEUESidelinkAggregateMaximumBitrate		PRESENCE optional }|
	{ ID id-PC5LinkAMBR								CRITICALITY ignore	TYPE BitRate											PRESENCE optional}|
	{ ID id-SLDRBs-ToBeSetup-List					CRITICALITY reject	TYPE SLDRBs-ToBeSetup-List							PRESENCE optional	}|
	{ ID id-ConditionalInterDUMobilityInformation	CRITICALITY reject	TYPE ConditionalInterDUMobilityInformation		PRESENCE optional}|
	{ ID id-ManagementBasedMDTPLMNList				CRITICALITY ignore	TYPE 		MDTPLMNList									PRESENCE optional }|
	{ ID id-ServingNID								CRITICALITY reject	TYPE NID												PRESENCE optional }|
	{ ID id-F1CTransferPath							CRITICALITY reject	TYPE F1CTransferPath									PRESENCE optional }|
	{ ID id-F1CTransferPathNRDC						CRITICALITY reject	TYPE F1CTransferPathNRDC								PRESENCE optional }|
	{ ID id-MDTPollutedMeasurementIndicator			CRITICALITY ignore	TYPE MDTPollutedMeasurementIndicator				PRESENCE optional }|
	{ ID id-SCGActivationRequest					CRITICALITY ignore	TYPE SCGActivationRequest								PRESENCE optional }|
	{ ID id-CG-SDTSessionInfoOld					CRITICALITY ignore	TYPE CG-SDTSessionInfo									PRESENCE optional }|
	{ ID id-FiveG-ProSeAuthorized					CRITICALITY ignore	TYPE FiveG-ProSeAuthorized							PRESENCE optional }|
	{ ID id-FiveG-ProSeUEPC5AggregateMaximumBitrate	CRITICALITY ignore	TYPE NRUESidelinkAggregateMaximumBitrate			PRESENCE optional }|
	{ ID id-FiveG-ProSePC5LinkAMBR					CRITICALITY ignore	TYPE BitRate											PRESENCE optional}|
	{ ID id-UuRLCChannelToBeSetupList				CRITICALITY reject	TYPE UuRLCChannelToBeSetupList						PRESENCE optional}|
	{ ID id-PC5RLCChannelToBeSetupList				CRITICALITY reject	TYPE PC5RLCChannelToBeSetupList						PRESENCE optional}|
	{ ID id-PathSwitchConfiguration					CRITICALITY ignore	TYPE PathSwitchConfiguration				 			PRESENCE optional	}|
	{ ID id-GNBDUUESliceMaximumBitRateList			CRITICALITY ignore  TYPE GNBDUUESliceMaximumBitRateList 				PRESENCE optional }|
	{ ID id-MulticastMBSSessionSetupList			CRITICALITY reject	TYPE MulticastMBSSessionList							PRESENCE optional }|
	{ ID id-UE-MulticastMRBs-ToBeSetup-List			CRITICALITY reject	TYPE UE-MulticastMRBs-ToBeSetup-List				PRESENCE optional	}|
	{ ID id-ServingCellMO-List						CRITICALITY ignore	TYPE ServingCellMO-List									PRESENCE optional	}|
	{ ID id-NetworkControlledRepeaterAuthorized		CRITICALITY ignore	TYPE NetworkControlledRepeaterAuthorized			PRESENCE optional	}|
	{ ID id-SDT-Volume-Threshold						CRITICALITY ignore	TYPE SDT-Volume-Threshold								PRESENCE optional  }|
	{ ID id-LTMInformation-Setup					CRITICALITY reject	TYPE LTMInformation-Setup								PRESENCE optional	}|
	{ ID id-LTMConfigurationIDMappingList			CRITICALITY reject	TYPE LTMConfigurationIDMappingList					PRESENCE optional	}|
	{ ID id-EarlySyncInformation-Request			CRITICALITY ignore	TYPE EarlySyncInformation-Request					PRESENCE optional	}|
	{ ID id-PathAdditionInformation				CRITICALITY reject	TYPE PathAdditionInformation							PRESENCE optional}|
	{ ID id-NRA2XServicesAuthorized					CRITICALITY ignore	TYPE NRA2XServicesAuthorized							PRESENCE optional }|
	{ ID id-LTEA2XServicesAuthorized				CRITICALITY ignore	TYPE LTEA2XServicesAuthorized								PRESENCE optional }|
	{ ID id-NRUESidelinkAggregateMaximumBitrateForA2X		CRITICALITY ignore	TYPE NRUESidelinkAggregateMaximumBitrate		PRESENCE optional }|
	{ ID id-LTEUESidelinkAggregateMaximumBitrateForA2X	CRITICALITY ignore	TYPE LTEUESidelinkAggregateMaximumBitrate		PRESENCE optional }|
	{ ID id-DLLBTFailureInformationRequest				CRITICALITY ignore	TYPE DLLBTFailureInformationRequest				PRESENCE optional }|
	{ ID id-SLPositioning-Ranging-Service-Info		CRITICALITY ignore	TYPE SLPositioning-Ranging-Service-Info						PRESENCE optional	}|
	{ ID id-NonIntegerDRXCycle						CRITICALITY ignore	TYPE NonIntegerDRXCycle									PRESENCE optional	}|
	{ ID id-LTMInformationSCGAdd					CRITICALITY reject	TYPE LTMInformationSCGAdd								PRESENCE optional	},
	...
}

Candidate-SpCell-List::= SEQUENCE (SIZE(1..maxnoofCandidateSpCells)) OF ProtocolIE-SingleContainer { { Candidate-SpCell-ItemIEs} }
SCell-ToBeSetup-List::= SEQUENCE (SIZE(1..maxnoofSCells)) OF ProtocolIE-SingleContainer { { SCell-ToBeSetup-ItemIEs} }
SRBs-ToBeSetup-List ::= SEQUENCE (SIZE(1..maxnoofSRBs)) OF ProtocolIE-SingleContainer { { SRBs-ToBeSetup-ItemIEs} }
DRBs-ToBeSetup-List ::= SEQUENCE (SIZE(1..maxnoofDRBs)) OF ProtocolIE-SingleContainer { { DRBs-ToBeSetup-ItemIEs} }
BHChannels-ToBeSetup-List ::= SEQUENCE (SIZE(1..maxnoofBHRLCChannels)) OF ProtocolIE-SingleContainer { { BHChannels-ToBeSetup-ItemIEs} }
SLDRBs-ToBeSetup-List ::= SEQUENCE (SIZE(1..maxnoofSLDRBs)) OF ProtocolIE-SingleContainer { { SLDRBs-ToBeSetup-ItemIEs} }
UE-MulticastMRBs-ToBeSetup-List ::= SEQUENCE (SIZE(1..maxnoofMRBsforUE)) OF ProtocolIE-SingleContainer { { UE-MulticastMRBs-ToBeSetup-ItemIEs} }
ServingCellMO-List ::= SEQUENCE (SIZE(1..maxnoofServingCellMOs)) OF ProtocolIE-SingleContainer { { ServingCellMO-List-ItemIEs} }

Candidate-SpCell-ItemIEs F1AP-PROTOCOL-IES ::= {
	{ ID id-Candidate-SpCell-Item					CRITICALITY ignore	TYPE Candidate-SpCell-Item						PRESENCE mandatory	},
	...
}


SCell-ToBeSetup-ItemIEs F1AP-PROTOCOL-IES ::= {
	{ ID id-SCell-ToBeSetup-Item						CRITICALITY ignore	TYPE SCell-ToBeSetup-Item					PRESENCE mandatory	},
	...
}

SRBs-ToBeSetup-ItemIEs F1AP-PROTOCOL-IES ::= {
	{ ID id-SRBs-ToBeSetup-Item		CRITICALITY reject		TYPE SRBs-ToBeSetup-Item		PRESENCE mandatory},
	...
}

DRBs-ToBeSetup-ItemIEs F1AP-PROTOCOL-IES ::= {
	{ ID id-DRBs-ToBeSetup-Item					CRITICALITY reject	TYPE DRBs-ToBeSetup-Item					PRESENCE mandatory},
	...
}

BHChannels-ToBeSetup-ItemIEs F1AP-PROTOCOL-IES ::= {
	{ ID id-BHChannels-ToBeSetup-Item					CRITICALITY reject	TYPE BHChannels-ToBeSetup-Item					PRESENCE mandatory},
	...
}

SLDRBs-ToBeSetup-ItemIEs F1AP-PROTOCOL-IES ::= {
	{ ID id-SLDRBs-ToBeSetup-Item					CRITICALITY reject	TYPE SLDRBs-ToBeSetup-Item					PRESENCE mandatory},
	...
}

UE-MulticastMRBs-ToBeSetup-ItemIEs F1AP-PROTOCOL-IES ::= {
	{ ID id-UE-MulticastMRBs-ToBeSetup-Item			CRITICALITY reject	TYPE UE-MulticastMRBs-ToBeSetup-Item			PRESENCE mandatory},
	...
}

ServingCellMO-List-ItemIEs F1AP-PROTOCOL-IES ::= {
	{ ID id-ServingCellMO-List-Item			CRITICALITY reject	TYPE ServingCellMO-List-Item	PRESENCE mandatory},
	...
}
-- **************************************************************
--
-- UE CONTEXT SETUP RESPONSE
--
-- **************************************************************

UEContextSetupResponse ::= SEQUENCE {
	protocolIEs			ProtocolIE-Container       { { UEContextSetupResponseIEs} },
	...
}


UEContextSetupResponseIEs F1AP-PROTOCOL-IES ::= {
	{ ID id-gNB-CU-UE-F1AP-ID						CRITICALITY reject	TYPE GNB-CU-UE-F1AP-ID								PRESENCE mandatory	}|
	{ ID id-gNB-DU-UE-F1AP-ID						CRITICALITY reject	TYPE GNB-DU-UE-F1AP-ID								PRESENCE mandatory	}|
	{ ID id-DUtoCURRCInformation					CRITICALITY reject	TYPE DUtoCURRCInformation							PRESENCE mandatory }|
	{ ID id-C-RNTI									CRITICALITY ignore	TYPE C-RNTI											PRESENCE optional	}|
	{ ID id-ResourceCoordinationTransferContainer	CRITICALITY ignore	TYPE ResourceCoordinationTransferContainer	PRESENCE optional	}|
	{ ID id-FullConfiguration						CRITICALITY reject	TYPE FullConfiguration								PRESENCE optional	}|
	{ ID id-DRBs-Setup-List							CRITICALITY ignore	TYPE DRBs-Setup-List								PRESENCE optional	}|
	{ ID id-SRBs-FailedToBeSetup-List				CRITICALITY ignore	TYPE SRBs-FailedToBeSetup-List					PRESENCE optional	}|
	{ ID id-DRBs-FailedToBeSetup-List				CRITICALITY ignore	TYPE DRBs-FailedToBeSetup-List					PRESENCE optional	}|
	{ ID id-SCell-FailedtoSetup-List				CRITICALITY ignore	TYPE SCell-FailedtoSetup-List					PRESENCE optional	}|
	{ ID id-InactivityMonitoringResponse			CRITICALITY reject	TYPE InactivityMonitoringResponse				PRESENCE optional	}|
	{ ID id-CriticalityDiagnostics					CRITICALITY ignore	TYPE CriticalityDiagnostics						PRESENCE optional	}|
	{ ID id-SRBs-Setup-List							CRITICALITY ignore	TYPE SRBs-Setup-List								PRESENCE optional	}|
	{ ID id-BHChannels-Setup-List					CRITICALITY ignore	TYPE BHChannels-Setup-List						PRESENCE optional	}|
	{ ID id-BHChannels-FailedToBeSetup-List			CRITICALITY ignore	TYPE BHChannels-FailedToBeSetup-List			PRESENCE optional	}|
	{ ID id-SLDRBs-Setup-List						CRITICALITY ignore	TYPE SLDRBs-Setup-List								PRESENCE optional	}|
	{ ID id-SLDRBs-FailedToBeSetup-List				CRITICALITY ignore	TYPE SLDRBs-FailedToBeSetup-List				PRESENCE optional	}|
	{ ID id-requestedTargetCellGlobalID				CRITICALITY reject	TYPE NRCGI											PRESENCE optional}|
	{ ID id-SCGActivationStatus						CRITICALITY ignore	TYPE SCGActivationStatus							PRESENCE optional }|
	{ ID id-UuRLCChannelSetupList					CRITICALITY ignore	TYPE UuRLCChannelSetupList						PRESENCE optional}|
	{ ID id-UuRLCChannelFailedToBeSetupList			CRITICALITY ignore	TYPE UuRLCChannelFailedToBeSetupList			PRESENCE optional}|
	{ ID id-PC5RLCChannelSetupList					CRITICALITY ignore	TYPE PC5RLCChannelSetupList						PRESENCE optional}|
	{ ID id-PC5RLCChannelFailedToBeSetupList		CRITICALITY ignore	TYPE PC5RLCChannelFailedToBeSetupList			PRESENCE optional}|
	{ ID id-ServingCellMO-encoded-in-CGC-List		CRITICALITY ignore	TYPE ServingCellMO-encoded-in-CGC-List			PRESENCE optional}|
	{ ID id-UE-MulticastMRBs-Setupnew-List			CRITICALITY reject	TYPE UE-MulticastMRBs-Setupnew-List				PRESENCE optional}|
	{ ID id-DedicatedSIDeliveryIndication			CRITICALITY ignore	TYPE DedicatedSIDeliveryIndication				PRESENCE optional}|
	{ ID id-Configured-BWP-List						CRITICALITY ignore	TYPE Configured-BWP-List								PRESENCE optional}|
	{ ID id-EarlySyncInformation					CRITICALITY ignore	TYPE EarlySyncInformation							PRESENCE optional	}|
	{ ID id-LTMConfiguration						CRITICALITY ignore	TYPE LTMConfiguration								PRESENCE optional	}|
	{ ID id-S-CPAC-Configuration					CRITICALITY ignore	TYPE S-CPAC-Configuration							PRESENCE optional	},
	...
}

DRBs-Setup-List ::= SEQUENCE (SIZE(1..maxnoofDRBs)) OF ProtocolIE-SingleContainer { { DRBs-Setup-ItemIEs} }


SRBs-FailedToBeSetup-List ::= SEQUENCE (SIZE(1..maxnoofSRBs)) OF ProtocolIE-SingleContainer { { SRBs-FailedToBeSetup-ItemIEs} }
DRBs-FailedToBeSetup-List ::= SEQUENCE (SIZE(1..maxnoofDRBs)) OF ProtocolIE-SingleContainer { { DRBs-FailedToBeSetup-ItemIEs} }
SCell-FailedtoSetup-List ::= SEQUENCE (SIZE(1..maxnoofSCells)) OF ProtocolIE-SingleContainer { { SCell-FailedtoSetup-ItemIEs} }
SRBs-Setup-List ::= SEQUENCE (SIZE(1..maxnoofSRBs)) OF ProtocolIE-SingleContainer { { SRBs-Setup-ItemIEs} }
BHChannels-Setup-List ::= SEQUENCE (SIZE(1..maxnoofBHRLCChannels)) OF ProtocolIE-SingleContainer { { BHChannels-Setup-ItemIEs} }
BHChannels-FailedToBeSetup-List ::= SEQUENCE (SIZE(1..maxnoofBHRLCChannels)) OF ProtocolIE-SingleContainer { { BHChannels-FailedToBeSetup-ItemIEs} }

DRBs-Setup-ItemIEs F1AP-PROTOCOL-IES ::= {
	{ ID id-DRBs-Setup-Item						CRITICALITY ignore	TYPE DRBs-Setup-Item						PRESENCE mandatory},
	...
}

SRBs-Setup-ItemIEs F1AP-PROTOCOL-IES ::= {
	{ ID id-SRBs-Setup-Item						CRITICALITY ignore	TYPE SRBs-Setup-Item						PRESENCE mandatory},
	...
}

SRBs-FailedToBeSetup-ItemIEs F1AP-PROTOCOL-IES ::= {
	{ ID id-SRBs-FailedToBeSetup-Item		CRITICALITY ignore		TYPE SRBs-FailedToBeSetup-Item		PRESENCE mandatory},
	...
}


DRBs-FailedToBeSetup-ItemIEs F1AP-PROTOCOL-IES ::= {
	{ ID id-DRBs-FailedToBeSetup-Item		CRITICALITY ignore	TYPE DRBs-FailedToBeSetup-Item			PRESENCE mandatory},
	...
}

SCell-FailedtoSetup-ItemIEs F1AP-PROTOCOL-IES ::= {
	{ ID id-SCell-FailedtoSetup-Item			CRITICALITY ignore	TYPE SCell-FailedtoSetup-Item			PRESENCE mandatory},
	...
}

BHChannels-Setup-ItemIEs F1AP-PROTOCOL-IES ::= {
	{ ID id-BHChannels-Setup-Item						CRITICALITY ignore	TYPE BHChannels-Setup-Item						PRESENCE mandatory},
	...
}

BHChannels-FailedToBeSetup-ItemIEs F1AP-PROTOCOL-IES ::= {
	{ ID id-BHChannels-FailedToBeSetup-Item						CRITICALITY ignore	TYPE BHChannels-FailedToBeSetup-Item		PRESENCE mandatory},
	...
}

SLDRBs-Setup-List ::= SEQUENCE (SIZE(1..maxnoofSLDRBs)) OF ProtocolIE-SingleContainer { { SLDRBs-Setup-ItemIEs} }

SLDRBs-FailedToBeSetup-List ::= SEQUENCE (SIZE(1..maxnoofSLDRBs)) OF ProtocolIE-SingleContainer { { SLDRBs-FailedToBeSetup-ItemIEs} }

SLDRBs-Setup-ItemIEs F1AP-PROTOCOL-IES ::= {
	{ ID id-SLDRBs-Setup-Item						CRITICALITY ignore	TYPE SLDRBs-Setup-Item						PRESENCE mandatory},
	...
}

SLDRBs-FailedToBeSetup-ItemIEs F1AP-PROTOCOL-IES ::= {
	{ ID id-SLDRBs-FailedToBeSetup-Item		CRITICALITY ignore	TYPE SLDRBs-FailedToBeSetup-Item			PRESENCE mandatory},
	...
}

UE-MulticastMRBs-Setupnew-List ::= SEQUENCE (SIZE(1..maxnoofMRBsforUE)) OF ProtocolIE-SingleContainer { { UE-MulticastMRBs-Setupnew-ItemIEs } }

UE-MulticastMRBs-Setupnew-ItemIEs F1AP-PROTOCOL-IES ::= {
	{ ID id-UE-MulticastMRBs-Setupnew-Item		CRITICALITY reject	TYPE UE-MulticastMRBs-Setupnew-Item		PRESENCE mandatory},
	...
}


-- **************************************************************
--
-- UE CONTEXT SETUP FAILURE
--
-- **************************************************************

UEContextSetupFailure ::= SEQUENCE {
	protocolIEs			ProtocolIE-Container       { { UEContextSetupFailureIEs} },
	...
}

UEContextSetupFailureIEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY ignore	TYPE GNB-DU-UE-F1AP-ID			PRESENCE optional	}|
	{ ID id-Cause						CRITICALITY ignore	TYPE Cause						PRESENCE mandatory	}|
	{ ID id-CriticalityDiagnostics		CRITICALITY ignore	TYPE CriticalityDiagnostics		PRESENCE optional	}|
	{ ID id-Potential-SpCell-List		CRITICALITY ignore	TYPE Potential-SpCell-List		PRESENCE optional	}|
	{ ID id-requestedTargetCellGlobalID	CRITICALITY reject	TYPE NRCGI						PRESENCE optional},
	...
}

Potential-SpCell-List::= SEQUENCE (SIZE(0..maxnoofPotentialSpCells)) OF ProtocolIE-SingleContainer { { Potential-SpCell-ItemIEs} }

Potential-SpCell-ItemIEs F1AP-PROTOCOL-IES ::= {
	{ ID id-Potential-SpCell-Item				CRITICALITY ignore	TYPE Potential-SpCell-Item					PRESENCE mandatory	},
	...
}

-- **************************************************************
--
-- UE Context Release Request ELEMENTARY PROCEDURE
--
-- **************************************************************

-- **************************************************************
--
-- UE Context Release Request
--
-- **************************************************************

UEContextReleaseRequest ::= SEQUENCE {
	protocolIEs			ProtocolIE-Container       {{ UEContextReleaseRequestIEs}},
	...
}

UEContextReleaseRequestIEs F1AP-PROTOCOL-IES ::= {
	{ ID id-gNB-CU-UE-F1AP-ID				CRITICALITY reject	TYPE GNB-CU-UE-F1AP-ID				PRESENCE mandatory	}|
	{ ID id-gNB-DU-UE-F1AP-ID				CRITICALITY reject	TYPE GNB-DU-UE-F1AP-ID				PRESENCE mandatory	}|
	{ ID id-Cause							CRITICALITY ignore	TYPE Cause							PRESENCE mandatory	}|
	{ ID id-targetCellsToCancel				CRITICALITY reject	TYPE TargetCellList					PRESENCE optional		}|
	{ ID id-LTMCells-ToBeReleased-List		CRITICALITY reject	TYPE LTMCells-ToBeReleased-List		PRESENCE optional	},
	...
}


-- **************************************************************
--
-- UE Context Release (gNB-CU initiated) ELEMENTARY PROCEDURE
--
-- **************************************************************

-- **************************************************************
--
-- UE CONTEXT RELEASE COMMAND
--
-- **************************************************************

UEContextReleaseCommand ::= SEQUENCE {
	protocolIEs			ProtocolIE-Container       { { UEContextReleaseCommandIEs} },
	...
}

UEContextReleaseCommandIEs F1AP-PROTOCOL-IES ::= {
	{ ID id-gNB-CU-UE-F1AP-ID				CRITICALITY reject	TYPE GNB-CU-UE-F1AP-ID				PRESENCE mandatory	}|
	{ ID id-gNB-DU-UE-F1AP-ID				CRITICALITY reject	TYPE GNB-DU-UE-F1AP-ID				PRESENCE mandatory	}|
	{ ID id-Cause							CRITICALITY ignore	TYPE Cause							PRESENCE mandatory	}|
	{ ID id-RRCContainer					CRITICALITY ignore	TYPE RRCContainer					PRESENCE optional	}|
	{ ID id-SRBID							CRITICALITY ignore	TYPE SRBID							PRESENCE conditional	}|
	-- The above IE shall be present if the RRC container IE is present.
	{ ID id-oldgNB-DU-UE-F1AP-ID			CRITICALITY ignore	TYPE GNB-DU-UE-F1AP-ID				PRESENCE optional	}|
	{ ID id-ExecuteDuplication				CRITICALITY ignore	TYPE ExecuteDuplication				PRESENCE optional}|
	{ ID id-RRCDeliveryStatusRequest		CRITICALITY ignore	TYPE RRCDeliveryStatusRequest		PRESENCE optional }|
	{ ID id-targetCellsToCancel				CRITICALITY reject	TYPE TargetCellList					PRESENCE optional}|
	{ ID id-PosContextRevIndication			CRITICALITY ignore	TYPE PosContextRevIndication			PRESENCE optional}|
	{ ID id-CG-SDTKeptIndicator				CRITICALITY ignore	TYPE CG-SDTKeptIndicator			PRESENCE optional}|
	{ ID id-LTMCells-ToBeReleased-List		CRITICALITY reject	TYPE LTMCells-ToBeReleased-List		PRESENCE optional	}|
	{ ID id-DLLBTFailureInformationRequest	CRITICALITY ignore	TYPE DLLBTFailureInformationRequest	PRESENCE optional},
	...
}

-- **************************************************************
--
-- UE CONTEXT RELEASE COMPLETE
--
-- **************************************************************

UEContextReleaseComplete ::= SEQUENCE {
	protocolIEs			ProtocolIE-Container       { { UEContextReleaseCompleteIEs} },
	...
}


UEContextReleaseCompleteIEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-CriticalityDiagnostics		CRITICALITY ignore	TYPE CriticalityDiagnostics		PRESENCE optional	}|
	{ ID id-Recommended-SSBs-for-Paging-List		CRITICALITY ignore	TYPE Recommended-SSBs-for-Paging-List		PRESENCE optional	},
	...
}

-- **************************************************************
--
-- UE Context Modification ELEMENTARY PROCEDURE
--
-- **************************************************************

-- **************************************************************
--
-- UE CONTEXT MODIFICATION REQUEST
--
-- **************************************************************

UEContextModificationRequest ::= SEQUENCE {
	protocolIEs			ProtocolIE-Container       { { UEContextModificationRequestIEs} },
	...
}

UEContextModificationRequestIEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY reject	TYPE GNB-DU-UE-F1AP-ID									PRESENCE mandatory	}|
	{ ID id-SpCell-ID								CRITICALITY ignore	TYPE NRCGI												PRESENCE optional	}|
	{ ID id-ServCellIndex							CRITICALITY reject	TYPE ServCellIndex										PRESENCE optional	}|
	{ ID id-SpCellULConfigured						CRITICALITY ignore	TYPE CellULConfigured									PRESENCE optional	}|
	{ ID id-DRXCycle								CRITICALITY ignore	TYPE DRXCycle											PRESENCE optional	}|
	{ ID id-CUtoDURRCInformation					CRITICALITY reject	TYPE CUtoDURRCInformation								PRESENCE optional	}|
	{ ID id-TransmissionActionIndicator				CRITICALITY ignore	TYPE TransmissionActionIndicator					PRESENCE optional	}|
	{ ID id-ResourceCoordinationTransferContainer	CRITICALITY ignore	TYPE ResourceCoordinationTransferContainer		PRESENCE optional	}|
	{ ID id-RRCReconfigurationCompleteIndicator		CRITICALITY ignore	TYPE RRCReconfigurationCompleteIndicator			PRESENCE optional	}|
	{ ID id-RRCContainer							CRITICALITY reject	TYPE RRCContainer										PRESENCE optional	}|
	{ ID id-SCell-ToBeSetupMod-List					CRITICALITY ignore	TYPE SCell-ToBeSetupMod-List							PRESENCE optional	}|
	{ ID id-SCell-ToBeRemoved-List					CRITICALITY ignore	TYPE SCell-ToBeRemoved-List 							PRESENCE optional }|
	{ ID id-SRBs-ToBeSetupMod-List					CRITICALITY reject	TYPE SRBs-ToBeSetupMod-List							PRESENCE optional	}|
	{ ID id-DRBs-ToBeSetupMod-List					CRITICALITY reject	TYPE DRBs-ToBeSetupMod-List							PRESENCE optional	}|
	{ ID id-DRBs-ToBeModified-List					CRITICALITY reject	TYPE DRBs-ToBeModified-List							PRESENCE optional	}|
	{ ID id-SRBs-ToBeReleased-List					CRITICALITY reject	TYPE SRBs-ToBeReleased-List							PRESENCE optional	}|
	{ ID id-DRBs-ToBeReleased-List					CRITICALITY reject	TYPE DRBs-ToBeReleased-List							PRESENCE optional	}|
	{ ID id-InactivityMonitoringRequest				CRITICALITY reject	TYPE InactivityMonitoringRequest					PRESENCE optional	}|
	{ ID id-RAT-FrequencyPriorityInformation		CRITICALITY reject	TYPE RAT-FrequencyPriorityInformation				PRESENCE optional	}|
	{ ID id-DRXConfigurationIndicator				CRITICALITY ignore	TYPE DRXConfigurationIndicator						PRESENCE optional	}|
	{ ID id-RLCFailureIndication					CRITICALITY ignore	TYPE RLCFailureIndication								PRESENCE optional	}|
	{ ID id-UplinkTxDirectCurrentListInformation	CRITICALITY ignore	TYPE UplinkTxDirectCurrentListInformation		PRESENCE optional	}|
	{ ID id-GNB-DUConfigurationQuery				CRITICALITY reject	TYPE GNB-DUConfigurationQuery						PRESENCE optional	}|
	{ ID id-GNB-DU-UE-AMBR-UL						CRITICALITY ignore	TYPE BitRate											PRESENCE optional	}|
	{ ID id-ExecuteDuplication						CRITICALITY ignore	TYPE ExecuteDuplication									PRESENCE optional}|
	{ ID id-RRCDeliveryStatusRequest				CRITICALITY ignore	TYPE RRCDeliveryStatusRequest						PRESENCE optional }|
	{ ID id-ResourceCoordinationTransferInformation	CRITICALITY ignore	TYPE ResourceCoordinationTransferInformation	PRESENCE optional	}|
	{ ID id-ServingCellMO							CRITICALITY ignore	TYPE ServingCellMO										PRESENCE optional	}|
	{ ID id-NeedforGap								CRITICALITY ignore	TYPE NeedforGap											PRESENCE optional	}|
	{ ID id-FullConfiguration						CRITICALITY reject	TYPE FullConfiguration									PRESENCE optional	}|
	{ ID id-AdditionalRRMPriorityIndex				CRITICALITY ignore	TYPE AdditionalRRMPriorityIndex						PRESENCE optional }|
	{ ID id-LowerLayerPresenceStatusChange			CRITICALITY ignore	TYPE LowerLayerPresenceStatusChange				PRESENCE optional	}|
	{ ID id-BHChannels-ToBeSetupMod-List			CRITICALITY reject	TYPE BHChannels-ToBeSetupMod-List					PRESENCE optional	}|
	{ ID id-BHChannels-ToBeModified-List			CRITICALITY reject	TYPE BHChannels-ToBeModified-List					PRESENCE optional	}|
	{ ID id-BHChannels-ToBeReleased-List			CRITICALITY reject	TYPE BHChannels-ToBeReleased-List					PRESENCE optional	}|
	{ ID id-NRV2XServicesAuthorized					CRITICALITY ignore	TYPE NRV2XServicesAuthorized							PRESENCE optional }|
	{ ID id-LTEV2XServicesAuthorized				CRITICALITY ignore	TYPE LTEV2XServicesAuthorized						PRESENCE optional }|
	{ ID id-NRUESidelinkAggregateMaximumBitrate		CRITICALITY ignore	TYPE NRUESidelinkAggregateMaximumBitrate			PRESENCE optional }|
	{ ID id-LTEUESidelinkAggregateMaximumBitrate	CRITICALITY ignore	TYPE LTEUESidelinkAggregateMaximumBitrate		PRESENCE optional }|
	{ ID id-PC5LinkAMBR								CRITICALITY ignore	TYPE BitRate											PRESENCE optional}|
	{ ID id-SLDRBs-ToBeSetupMod-List				CRITICALITY reject	TYPE SLDRBs-ToBeSetupMod-List						PRESENCE optional	}|
	{ ID id-SLDRBs-ToBeModified-List				CRITICALITY reject	TYPE SLDRBs-ToBeModified-List						PRESENCE optional	}|
	{ ID id-SLDRBs-ToBeReleased-List				CRITICALITY reject	TYPE SLDRBs-ToBeReleased-List						PRESENCE optional	}|
	{ ID id-ConditionalIntraDUMobilityInformation	CRITICALITY reject	TYPE ConditionalIntraDUMobilityInformation		PRESENCE optional}|
	{ ID id-F1CTransferPath							CRITICALITY reject	TYPE F1CTransferPath									PRESENCE optional }|
	{ ID id-SCGIndicator							CRITICALITY ignore	TYPE SCGIndicator										PRESENCE optional	}|
	{ ID id-UplinkTxDirectCurrentTwoCarrierListInfo		CRITICALITY ignore	TYPE UplinkTxDirectCurrentTwoCarrierListInfo	PRESENCE optional	}|
	{ ID id-IABConditionalRRCMessageDeliveryIndication				CRITICALITY reject	TYPE IABConditionalRRCMessageDeliveryIndication							PRESENCE optional	}|
	{ ID id-F1CTransferPathNRDC							CRITICALITY reject	TYPE F1CTransferPathNRDC								PRESENCE optional }|
	{ ID id-MDTPollutedMeasurementIndicator				CRITICALITY ignore	TYPE MDTPollutedMeasurementIndicator				PRESENCE optional }|
	{ ID id-SCGActivationRequest						CRITICALITY ignore	TYPE SCGActivationRequest							PRESENCE optional }|
	{ ID id-CG-SDTQueryIndication						CRITICALITY ignore	TYPE CG-SDTQueryIndication							PRESENCE optional	}|
	{ ID id-FiveG-ProSeAuthorized						CRITICALITY ignore	TYPE FiveG-ProSeAuthorized							PRESENCE optional }|
	{ ID id-FiveG-ProSeUEPC5AggregateMaximumBitrate		CRITICALITY ignore	TYPE NRUESidelinkAggregateMaximumBitrate		PRESENCE optional }|
	{ ID id-FiveG-ProSePC5LinkAMBR						CRITICALITY ignore	TYPE BitRate											PRESENCE optional}|
	{ ID id-UpdatedRemoteUELocalID						CRITICALITY ignore	TYPE RemoteUELocalID				 					PRESENCE optional	}|
	{ ID id-UuRLCChannelToBeSetupList					CRITICALITY reject	TYPE UuRLCChannelToBeSetupList						PRESENCE optional}|
	{ ID id-UuRLCChannelToBeModifiedList				CRITICALITY reject	TYPE UuRLCChannelToBeModifiedList					PRESENCE optional}|
	{ ID id-UuRLCChannelToBeReleasedList				CRITICALITY reject	TYPE UuRLCChannelToBeReleasedList					PRESENCE optional}|
	{ ID id-PC5RLCChannelToBeSetupList					CRITICALITY reject	TYPE PC5RLCChannelToBeSetupList					PRESENCE optional}|
	{ ID id-PC5RLCChannelToBeModifiedList				CRITICALITY reject	TYPE PC5RLCChannelToBeModifiedList				PRESENCE optional}|
	{ ID id-PC5RLCChannelToBeReleasedList				CRITICALITY reject	TYPE PC5RLCChannelToBeReleasedList				PRESENCE optional}|
	{ ID id-PathSwitchConfiguration						CRITICALITY ignore	TYPE PathSwitchConfiguration				 		PRESENCE optional	}|
	{ ID id-GNBDUUESliceMaximumBitRateList				CRITICALITY ignore	TYPE GNBDUUESliceMaximumBitRateList				PRESENCE optional }|
	{ ID id-MulticastMBSSessionSetupList				CRITICALITY reject	TYPE MulticastMBSSessionList						PRESENCE optional }|
	{ ID id-MulticastMBSSessionRemoveList				CRITICALITY reject	TYPE MulticastMBSSessionList						PRESENCE optional }|
	{ ID id-UE-MulticastMRBs-ToBeSetup-atModify-List	CRITICALITY reject	TYPE UE-MulticastMRBs-ToBeSetup-atModify-List	PRESENCE optional	}|
	{ ID id-UE-MulticastMRBs-ToBeReleased-List			CRITICALITY reject	TYPE UE-MulticastMRBs-ToBeReleased-List			PRESENCE optional	}|
	{ ID id-SLDRXCycleList								CRITICALITY ignore  TYPE SLDRXCycleList 										PRESENCE optional }|
	{ ID id-ManagementBasedMDTPLMNModificationList		CRITICALITY ignore	TYPE MDTPLMNModificationList						PRESENCE optional }|
	{ ID id-SDTBearerConfigurationQueryIndication		CRITICALITY ignore	TYPE SDTBearerConfigurationQueryIndication		PRESENCE optional }|
	{ ID id-DAPS-HO-Status								CRITICALITY ignore	TYPE DAPS-HO-Status										PRESENCE optional }|
	{ ID id-ServingCellMO-List							CRITICALITY ignore	TYPE ServingCellMO-List								PRESENCE optional	}|
	{ ID id-UlTxDirectCurrentMoreCarrierInformation	    CRITICALITY ignore	TYPE UlTxDirectCurrentMoreCarrierInformation	PRESENCE optional	}|
	{ ID id-CPACMCGInformation							CRITICALITY ignore	TYPE CPACMCGInformation								PRESENCE optional }|
	{ ID id-NetworkControlledRepeaterAuthorized			CRITICALITY ignore	TYPE NetworkControlledRepeaterAuthorized			PRESENCE optional	}|
	{ ID id-SDT-Volume-Threshold							CRITICALITY ignore	TYPE SDT-Volume-Threshold								PRESENCE optional  }|
	{ ID id-LTMInformation-Modify						CRITICALITY reject	TYPE LTMInformation-Modify							PRESENCE optional	}|
	{ ID id-LTMCFRAResourceConfig-List					CRITICALITY ignore	TYPE LTMCFRAResourceConfig-List					PRESENCE optional	}|
	{ ID id-LTMConfigurationIDMappingList				CRITICALITY reject	TYPE LTMConfigurationIDMappingList				PRESENCE optional	}|
	{ ID id-EarlySyncInformation-Request				CRITICALITY ignore	TYPE EarlySyncInformation-Request					PRESENCE optional	}|
	{ ID id-EarlySyncCandidateCellInformation-List		CRITICALITY ignore	TYPE EarlySyncCandidateCellInformation-List		PRESENCE optional	}|
	{ ID id-EarlySyncServingCellInformation				CRITICALITY ignore	TYPE EarlySyncServingCellInformation				PRESENCE optional }|
	{ ID id-LTMCells-ToBeReleased-List					CRITICALITY reject	TYPE LTMCells-ToBeReleased-List					PRESENCE optional	}|
	{ ID id-PathAdditionInformation					CRITICALITY reject	TYPE PathAdditionInformation								PRESENCE optional}|
	{ ID id-NRA2XServicesAuthorized						CRITICALITY ignore	TYPE NRA2XServicesAuthorized							PRESENCE optional }|
	{ ID id-LTEA2XServicesAuthorized						CRITICALITY ignore	TYPE LTEA2XServicesAuthorized							PRESENCE optional }|
	{ ID id-NRUESidelinkAggregateMaximumBitrateForA2X		CRITICALITY ignore	TYPE NRUESidelinkAggregateMaximumBitrate			PRESENCE optional }|
	{ ID id-LTEUESidelinkAggregateMaximumBitrateForA2X	CRITICALITY ignore	TYPE LTEUESidelinkAggregateMaximumBitrate			PRESENCE optional }|
	{ ID id-DLLBTFailureInformationRequest				CRITICALITY ignore	TYPE DLLBTFailureInformationRequest				PRESENCE optional }|
	{ ID id-SLPositioning-Ranging-Service-Info		CRITICALITY ignore	TYPE SLPositioning-Ranging-Service-Info						PRESENCE optional	}|
	{ ID id-NonIntegerDRXCycle						CRITICALITY ignore	TYPE NonIntegerDRXCycle									PRESENCE optional	}|
	{ ID id-LTMResetInformation						CRITICALITY ignore	TYPE LTMResetInformation								PRESENCE optional	}|
	{ ID id-LTMTCIStatesConfigurationsList			CRITICALITY reject	TYPE LTMTCIStatesConfigurationsList				PRESENCE optional	}|
	{ ID id-LTMSecurityInformation					CRITICALITY reject	TYPE LTMSecurityInformation							PRESENCE optional	}|
	{ ID id-LTMInformationSCGMod					CRITICALITY reject	TYPE LTMInformationSCGMod								PRESENCE optional	}|
	{ ID id-InterSNLTMMCGInformation				CRITICALITY ignore	TYPE InterSNLTMMCGInformation						PRESENCE optional	},
	...
}

SCell-ToBeSetupMod-List::= SEQUENCE (SIZE(1..maxnoofSCells)) OF ProtocolIE-SingleContainer { { SCell-ToBeSetupMod-ItemIEs} }
SCell-ToBeRemoved-List::= SEQUENCE (SIZE(1..maxnoofSCells)) OF ProtocolIE-SingleContainer { { SCell-ToBeRemoved-ItemIEs} }
SRBs-ToBeSetupMod-List ::= SEQUENCE (SIZE(1..maxnoofSRBs)) OF ProtocolIE-SingleContainer { { SRBs-ToBeSetupMod-ItemIEs} }
DRBs-ToBeSetupMod-List ::= SEQUENCE (SIZE(1..maxnoofDRBs)) OF ProtocolIE-SingleContainer { { DRBs-ToBeSetupMod-ItemIEs} }
BHChannels-ToBeSetupMod-List ::= SEQUENCE (SIZE(1..maxnoofBHRLCChannels)) OF ProtocolIE-SingleContainer { { BHChannels-ToBeSetupMod-ItemIEs} }

DRBs-ToBeModified-List ::= SEQUENCE (SIZE(1..maxnoofDRBs)) OF ProtocolIE-SingleContainer { { DRBs-ToBeModified-ItemIEs} }
BHChannels-ToBeModified-List ::= SEQUENCE (SIZE(1..maxnoofBHRLCChannels)) OF ProtocolIE-SingleContainer { { BHChannels-ToBeModified-ItemIEs} }
SRBs-ToBeReleased-List ::= SEQUENCE (SIZE(1..maxnoofSRBs)) OF ProtocolIE-SingleContainer { { SRBs-ToBeReleased-ItemIEs} }
DRBs-ToBeReleased-List ::= SEQUENCE (SIZE(1..maxnoofDRBs)) OF ProtocolIE-SingleContainer { { DRBs-ToBeReleased-ItemIEs} }
BHChannels-ToBeReleased-List ::= SEQUENCE (SIZE(1..maxnoofBHRLCChannels)) OF ProtocolIE-SingleContainer { { BHChannels-ToBeReleased-ItemIEs} }
UE-MulticastMRBs-ToBeSetup-atModify-List ::= SEQUENCE (SIZE(1..maxnoofMRBsforUE)) OF
										ProtocolIE-SingleContainer { { UE-MulticastMRBs-ToBeSetup-atModify-ItemIEs} }

UE-MulticastMRBs-ToBeReleased-List ::= SEQUENCE (SIZE(1..maxnoofMRBsforUE)) OF ProtocolIE-SingleContainer { { UE-MulticastMRBs-ToBeReleased-ItemIEs} }

SCell-ToBeSetupMod-ItemIEs F1AP-PROTOCOL-IES ::= {
	{ ID id-SCell-ToBeSetupMod-Item			CRITICALITY ignore	TYPE SCell-ToBeSetupMod-Item			PRESENCE mandatory	},
	...
}

SCell-ToBeRemoved-ItemIEs F1AP-PROTOCOL-IES ::= {
	{ ID id-SCell-ToBeRemoved-Item			CRITICALITY ignore	TYPE SCell-ToBeRemoved-Item			PRESENCE mandatory	},
	...
}


SRBs-ToBeSetupMod-ItemIEs F1AP-PROTOCOL-IES ::= {
	{ ID id-SRBs-ToBeSetupMod-Item		CRITICALITY reject	TYPE SRBs-ToBeSetupMod-Item		PRESENCE mandatory},
	...
}


DRBs-ToBeSetupMod-ItemIEs F1AP-PROTOCOL-IES ::= {
	{ ID id-DRBs-ToBeSetupMod-Item		CRITICALITY reject	TYPE DRBs-ToBeSetupMod-Item		PRESENCE mandatory},
	...
}

DRBs-ToBeModified-ItemIEs F1AP-PROTOCOL-IES ::= {
	{ ID id-DRBs-ToBeModified-Item		CRITICALITY reject	TYPE DRBs-ToBeModified-Item			PRESENCE mandatory},
	...
}


SRBs-ToBeReleased-ItemIEs F1AP-PROTOCOL-IES ::= {
	{ ID id-SRBs-ToBeReleased-Item	CRITICALITY reject	TYPE SRBs-ToBeReleased-Item		PRESENCE mandatory},
	...
}

DRBs-ToBeReleased-ItemIEs F1AP-PROTOCOL-IES ::= {
	{ ID id-DRBs-ToBeReleased-Item		CRITICALITY reject	TYPE DRBs-ToBeReleased-Item		PRESENCE mandatory},
	...
}

BHChannels-ToBeSetupMod-ItemIEs F1AP-PROTOCOL-IES ::= {
	{ ID id-BHChannels-ToBeSetupMod-Item		CRITICALITY reject	TYPE BHChannels-ToBeSetupMod-Item		PRESENCE mandatory},
	...
}

BHChannels-ToBeModified-ItemIEs F1AP-PROTOCOL-IES ::= {
	{ ID id-BHChannels-ToBeModified-Item		CRITICALITY reject	TYPE BHChannels-ToBeModified-Item		PRESENCE mandatory},
	...
}

BHChannels-ToBeReleased-ItemIEs F1AP-PROTOCOL-IES ::= {
	{ ID id-BHChannels-ToBeReleased-Item		CRITICALITY reject	TYPE BHChannels-ToBeReleased-Item		PRESENCE mandatory},
	...
}

SLDRBs-ToBeSetupMod-List ::= SEQUENCE (SIZE(1..maxnoofSLDRBs)) OF ProtocolIE-SingleContainer { { SLDRBs-ToBeSetupMod-ItemIEs} }
SLDRBs-ToBeModified-List ::= SEQUENCE (SIZE(1..maxnoofSLDRBs)) OF ProtocolIE-SingleContainer { { SLDRBs-ToBeModified-ItemIEs} }
SLDRBs-ToBeReleased-List ::= SEQUENCE (SIZE(1..maxnoofSLDRBs)) OF ProtocolIE-SingleContainer { { SLDRBs-ToBeReleased-ItemIEs} }

SLDRBs-ToBeSetupMod-ItemIEs F1AP-PROTOCOL-IES ::= {
	{ ID id-SLDRBs-ToBeSetupMod-Item		CRITICALITY reject	TYPE SLDRBs-ToBeSetupMod-Item		PRESENCE mandatory},
	...
}

SLDRBs-ToBeModified-ItemIEs F1AP-PROTOCOL-IES ::= {
	{ ID id-SLDRBs-ToBeModified-Item		CRITICALITY reject	TYPE SLDRBs-ToBeModified-Item		PRESENCE mandatory},
	...
}

SLDRBs-ToBeReleased-ItemIEs F1AP-PROTOCOL-IES ::= {
	{ ID id-SLDRBs-ToBeReleased-Item		CRITICALITY reject	TYPE SLDRBs-ToBeReleased-Item		PRESENCE mandatory},
	...
}

UE-MulticastMRBs-ToBeSetup-atModify-ItemIEs F1AP-PROTOCOL-IES ::= {
	{ ID id-UE-MulticastMRBs-ToBeSetup-atModify-Item	CRITICALITY reject	TYPE UE-MulticastMRBs-ToBeSetup-atModify-Item			PRESENCE mandatory},
	...
}


UE-MulticastMRBs-ToBeReleased-ItemIEs F1AP-PROTOCOL-IES ::= {
	{ ID id-UE-MulticastMRBs-ToBeReleased-Item		CRITICALITY reject	TYPE UE-MulticastMRBs-ToBeReleased-Item		PRESENCE mandatory},
	...
}

-- **************************************************************
--
-- UE CONTEXT MODIFICATION RESPONSE
--
-- **************************************************************

UEContextModificationResponse ::= SEQUENCE {
	protocolIEs			ProtocolIE-Container       { { UEContextModificationResponseIEs} },
	...
}


UEContextModificationResponseIEs F1AP-PROTOCOL-IES ::= {
	{ ID id-gNB-CU-UE-F1AP-ID						CRITICALITY reject	TYPE GNB-CU-UE-F1AP-ID								PRESENCE mandatory	}|
	{ ID id-gNB-DU-UE-F1AP-ID						CRITICALITY reject	TYPE GNB-DU-UE-F1AP-ID								PRESENCE mandatory	}|
	{ ID id-ResourceCoordinationTransferContainer	CRITICALITY ignore	TYPE ResourceCoordinationTransferContainer	PRESENCE optional	}|
	{ ID id-DUtoCURRCInformation					CRITICALITY reject	TYPE DUtoCURRCInformation							PRESENCE optional}|
	{ ID id-DRBs-SetupMod-List						CRITICALITY ignore	TYPE DRBs-SetupMod-List								PRESENCE optional}|
	{ ID id-DRBs-Modified-List						CRITICALITY ignore	TYPE DRBs-Modified-List								PRESENCE optional}|
	{ ID id-SRBs-FailedToBeSetupMod-List			CRITICALITY ignore	TYPE SRBs-FailedToBeSetupMod-List				PRESENCE optional	}|
	{ ID id-DRBs-FailedToBeSetupMod-List			CRITICALITY ignore	TYPE DRBs-FailedToBeSetupMod-List				PRESENCE optional	}|
	{ ID id-SCell-FailedtoSetupMod-List				CRITICALITY ignore	TYPE SCell-FailedtoSetupMod-List				PRESENCE optional	}|
	{ ID id-DRBs-FailedToBeModified-List			CRITICALITY ignore	TYPE DRBs-FailedToBeModified-List				PRESENCE optional	}|
	{ ID id-InactivityMonitoringResponse			CRITICALITY reject	TYPE InactivityMonitoringResponse				PRESENCE optional	}|
	{ ID id-CriticalityDiagnostics					CRITICALITY ignore	TYPE CriticalityDiagnostics						PRESENCE optional	}|
	{ ID id-C-RNTI									CRITICALITY ignore	TYPE C-RNTI											PRESENCE optional	}|
	{ ID id-Associated-SCell-List					CRITICALITY ignore  TYPE Associated-SCell-List						PRESENCE optional	}|
	{ ID id-SRBs-SetupMod-List						CRITICALITY ignore	TYPE SRBs-SetupMod-List								PRESENCE optional	}|
	{ ID id-SRBs-Modified-List						CRITICALITY ignore	TYPE SRBs-Modified-List								PRESENCE optional	}|
	{ ID id-FullConfiguration						CRITICALITY reject	TYPE FullConfiguration								PRESENCE optional	}|
	{ ID id-BHChannels-SetupMod-List				CRITICALITY ignore	TYPE BHChannels-SetupMod-List					PRESENCE optional}|
	{ ID id-BHChannels-Modified-List				CRITICALITY ignore	TYPE BHChannels-Modified-List					PRESENCE optional}|
	{ ID id-BHChannels-FailedToBeSetupMod-List		CRITICALITY ignore	TYPE BHChannels-FailedToBeSetupMod-List		PRESENCE optional	}|
	{ ID id-BHChannels-FailedToBeModified-List		CRITICALITY ignore	TYPE BHChannels-FailedToBeModified-List		PRESENCE optional	}|
	{ ID id-SLDRBs-SetupMod-List					CRITICALITY ignore	TYPE SLDRBs-SetupMod-List							PRESENCE optional	}|
	{ ID id-SLDRBs-Modified-List					CRITICALITY ignore	TYPE SLDRBs-Modified-List							PRESENCE optional	}|
	{ ID id-SLDRBs-FailedToBeSetupMod-List			CRITICALITY ignore	TYPE SLDRBs-FailedToBeSetupMod-List			PRESENCE optional	}|
	{ ID id-SLDRBs-FailedToBeModified-List			CRITICALITY ignore	TYPE SLDRBs-FailedToBeModified-List			PRESENCE optional	}|
	{ ID id-requestedTargetCellGlobalID				CRITICALITY reject	TYPE NRCGI											PRESENCE optional}|
	{ ID id-SCGActivationStatus						CRITICALITY ignore	TYPE SCGActivationStatus							PRESENCE optional }|
	{ ID id-UuRLCChannelSetupList					CRITICALITY ignore	TYPE UuRLCChannelSetupList						PRESENCE optional}|
	{ ID id-UuRLCChannelFailedToBeSetupList			CRITICALITY ignore	TYPE UuRLCChannelFailedToBeSetupList			PRESENCE optional}|
	{ ID id-UuRLCChannelModifiedList				CRITICALITY ignore	TYPE UuRLCChannelModifiedList					PRESENCE optional}|
	{ ID id-UuRLCChannelFailedToBeModifiedList		CRITICALITY ignore	TYPE UuRLCChannelFailedToBeModifiedList		PRESENCE optional}|
	{ ID id-PC5RLCChannelSetupList					CRITICALITY ignore	TYPE PC5RLCChannelSetupList						PRESENCE optional}|
	{ ID id-PC5RLCChannelFailedToBeSetupList		CRITICALITY ignore	TYPE PC5RLCChannelFailedToBeSetupList			PRESENCE optional}|
	{ ID id-PC5RLCChannelModifiedList				CRITICALITY ignore	TYPE PC5RLCChannelModifiedList					PRESENCE optional}|
	{ ID id-PC5RLCChannelFailedToBeModifiedList		CRITICALITY ignore	TYPE PC5RLCChannelFailedToBeModifiedList		PRESENCE optional}|
	{ ID id-SDTBearerConfigurationInfo				CRITICALITY ignore	TYPE SDTBearerConfigurationInfo					PRESENCE optional}|
	{ ID id-UE-MulticastMRBs-Setup-List				CRITICALITY reject	TYPE UE-MulticastMRBs-Setup-List				PRESENCE optional}|
	{ ID id-ServingCellMO-encoded-in-CGC-List		CRITICALITY ignore	TYPE ServingCellMO-encoded-in-CGC-List		PRESENCE optional}|
	{ ID id-DedicatedSIDeliveryIndication			CRITICALITY ignore	TYPE DedicatedSIDeliveryIndication				PRESENCE optional}|
	{ ID id-Configured-BWP-List						CRITICALITY ignore	TYPE Configured-BWP-List							PRESENCE optional}|
	{ ID id-EarlySyncInformation					CRITICALITY ignore	TYPE EarlySyncInformation							PRESENCE optional}|
	{ ID id-LTMConfiguration						CRITICALITY ignore	TYPE LTMConfiguration								PRESENCE optional}|
	{ ID id-S-CPAC-Configuration					CRITICALITY ignore	TYPE S-CPAC-Configuration							PRESENCE optional	}|
	{ ID id-TARemainingInfoList						CRITICALITY ignore	TYPE TARemainingInfoList							PRESENCE optional	},
	...
}


DRBs-SetupMod-List ::= SEQUENCE (SIZE(1..maxnoofDRBs)) OF ProtocolIE-SingleContainer { { DRBs-SetupMod-ItemIEs} }
DRBs-Modified-List::= SEQUENCE (SIZE(1..maxnoofDRBs)) OF ProtocolIE-SingleContainer { { DRBs-Modified-ItemIEs } }
SRBs-SetupMod-List ::= SEQUENCE (SIZE(1..maxnoofSRBs)) OF ProtocolIE-SingleContainer { { SRBs-SetupMod-ItemIEs} }
SRBs-Modified-List ::= SEQUENCE (SIZE(1..maxnoofSRBs)) OF ProtocolIE-SingleContainer { { SRBs-Modified-ItemIEs } }
DRBs-FailedToBeModified-List ::= SEQUENCE (SIZE(1..maxnoofDRBs)) OF ProtocolIE-SingleContainer { { DRBs-FailedToBeModified-ItemIEs} }
SRBs-FailedToBeSetupMod-List ::= SEQUENCE (SIZE(1..maxnoofSRBs)) OF ProtocolIE-SingleContainer { { SRBs-FailedToBeSetupMod-ItemIEs} }
DRBs-FailedToBeSetupMod-List ::= SEQUENCE (SIZE(1..maxnoofDRBs)) OF ProtocolIE-SingleContainer { { DRBs-FailedToBeSetupMod-ItemIEs} }
SCell-FailedtoSetupMod-List ::= SEQUENCE (SIZE(1..maxnoofSCells)) OF ProtocolIE-SingleContainer { { SCell-FailedtoSetupMod-ItemIEs} }
BHChannels-SetupMod-List ::= SEQUENCE (SIZE(1..maxnoofBHRLCChannels)) OF ProtocolIE-SingleContainer { { BHChannels-SetupMod-ItemIEs} }
BHChannels-Modified-List ::= SEQUENCE (SIZE(1..maxnoofBHRLCChannels)) OF ProtocolIE-SingleContainer { { BHChannels-Modified-ItemIEs } }
BHChannels-FailedToBeModified-List ::= SEQUENCE (SIZE(1..maxnoofBHRLCChannels)) OF ProtocolIE-SingleContainer { { BHChannels-FailedToBeModified-ItemIEs} }
BHChannels-FailedToBeSetupMod-List ::= SEQUENCE (SIZE(1..maxnoofBHRLCChannels)) OF ProtocolIE-SingleContainer { { BHChannels-FailedToBeSetupMod-ItemIEs} }

Associated-SCell-List ::= SEQUENCE (SIZE(1.. maxnoofSCells)) OF ProtocolIE-SingleContainer { { Associated-SCell-ItemIEs} }

DRBs-SetupMod-ItemIEs F1AP-PROTOCOL-IES ::= {
	{ ID id-DRBs-SetupMod-Item		CRITICALITY ignore		TYPE DRBs-SetupMod-Item		PRESENCE mandatory},
	...
}


DRBs-Modified-ItemIEs F1AP-PROTOCOL-IES ::= {
	{ ID id-DRBs-Modified-Item			CRITICALITY ignore	TYPE DRBs-Modified-Item		PRESENCE mandatory},
	...
}

SRBs-SetupMod-ItemIEs F1AP-PROTOCOL-IES ::= {
	{ ID id-SRBs-SetupMod-Item		CRITICALITY ignore		TYPE SRBs-SetupMod-Item		PRESENCE mandatory},
	...
}


SRBs-Modified-ItemIEs F1AP-PROTOCOL-IES ::= {
	{ ID id-SRBs-Modified-Item			CRITICALITY ignore	TYPE SRBs-Modified-Item		PRESENCE mandatory},
	...
}

SRBs-FailedToBeSetupMod-ItemIEs F1AP-PROTOCOL-IES ::= {
	{ ID id-SRBs-FailedToBeSetupMod-Item		CRITICALITY ignore	TYPE SRBs-FailedToBeSetupMod-Item		PRESENCE mandatory},
	...
}


DRBs-FailedToBeSetupMod-ItemIEs F1AP-PROTOCOL-IES ::= {
	{ ID id-DRBs-FailedToBeSetupMod-Item		CRITICALITY ignore	TYPE DRBs-FailedToBeSetupMod-Item		PRESENCE mandatory},
	...
}


DRBs-FailedToBeModified-ItemIEs F1AP-PROTOCOL-IES ::= {
	{ ID id-DRBs-FailedToBeModified-Item		CRITICALITY ignore	TYPE DRBs-FailedToBeModified-Item		PRESENCE mandatory},
	...
}

SCell-FailedtoSetupMod-ItemIEs F1AP-PROTOCOL-IES ::= {
	{ ID id-SCell-FailedtoSetupMod-Item			CRITICALITY ignore	TYPE SCell-FailedtoSetupMod-Item			PRESENCE mandatory},
	...
}

Associated-SCell-ItemIEs F1AP-PROTOCOL-IES ::= {
	{ ID id-Associated-SCell-Item			CRITICALITY ignore	TYPE Associated-SCell-Item			PRESENCE mandatory},
	...
}

BHChannels-SetupMod-ItemIEs F1AP-PROTOCOL-IES ::= {
	{ ID id-BHChannels-SetupMod-Item		CRITICALITY ignore		TYPE BHChannels-SetupMod-Item		PRESENCE mandatory},
	...
}


BHChannels-Modified-ItemIEs F1AP-PROTOCOL-IES ::= {
	{ ID id-BHChannels-Modified-Item		CRITICALITY ignore	TYPE BHChannels-Modified-Item		PRESENCE mandatory},
	...
}

BHChannels-FailedToBeSetupMod-ItemIEs F1AP-PROTOCOL-IES ::= {
	{ ID id-BHChannels-FailedToBeSetupMod-Item		CRITICALITY ignore	TYPE BHChannels-FailedToBeSetupMod-Item		PRESENCE mandatory},
	...
}

BHChannels-FailedToBeModified-ItemIEs F1AP-PROTOCOL-IES ::= {
	{ ID id-BHChannels-FailedToBeModified-Item		CRITICALITY ignore	TYPE BHChannels-FailedToBeModified-Item		PRESENCE mandatory},
	...
}

SLDRBs-SetupMod-List 			::= SEQUENCE (SIZE(1..maxnoofSLDRBs)) OF ProtocolIE-SingleContainer { { SLDRBs-SetupMod-ItemIEs} }
SLDRBs-Modified-List				::= SEQUENCE (SIZE(1..maxnoofSLDRBs)) OF ProtocolIE-SingleContainer { { SLDRBs-Modified-ItemIEs } }
SLDRBs-FailedToBeModified-List 	::= SEQUENCE (SIZE(1..maxnoofSLDRBs)) OF ProtocolIE-SingleContainer { { SLDRBs-FailedToBeModified-ItemIEs} }
SLDRBs-FailedToBeSetupMod-List 	::= SEQUENCE (SIZE(1..maxnoofSLDRBs)) OF ProtocolIE-SingleContainer { { SLDRBs-FailedToBeSetupMod-ItemIEs} }

SLDRBs-SetupMod-ItemIEs F1AP-PROTOCOL-IES ::= {
	{ ID id-SLDRBs-SetupMod-Item		CRITICALITY ignore		TYPE SLDRBs-SetupMod-Item		PRESENCE mandatory},
	...
}

SLDRBs-Modified-ItemIEs F1AP-PROTOCOL-IES ::= {
	{ ID id-SLDRBs-Modified-Item			CRITICALITY ignore	TYPE SLDRBs-Modified-Item		PRESENCE mandatory},
	...
}

SLDRBs-FailedToBeSetupMod-ItemIEs F1AP-PROTOCOL-IES ::= {
	{ ID id-SLDRBs-FailedToBeSetupMod-Item		CRITICALITY ignore	TYPE SLDRBs-FailedToBeSetupMod-Item		PRESENCE mandatory},
	...
}

SLDRBs-FailedToBeModified-ItemIEs F1AP-PROTOCOL-IES ::= {
	{ ID id-SLDRBs-FailedToBeModified-Item		CRITICALITY ignore	TYPE SLDRBs-FailedToBeModified-Item		PRESENCE mandatory},
	...
}

UE-MulticastMRBs-Setup-List ::= SEQUENCE (SIZE(1..maxnoofMRBsforUE)) OF ProtocolIE-SingleContainer { { UE-MulticastMRBs-Setup-ItemIEs } }

UE-MulticastMRBs-Setup-ItemIEs F1AP-PROTOCOL-IES ::= {
	{ ID id-UE-MulticastMRBs-Setup-Item		CRITICALITY reject	TYPE UE-MulticastMRBs-Setup-Item		PRESENCE mandatory},
	...
}


-- **************************************************************
--
-- UE CONTEXT MODIFICATION FAILURE
--
-- **************************************************************

UEContextModificationFailure ::= SEQUENCE {
	protocolIEs			ProtocolIE-Container       { { UEContextModificationFailureIEs} },
	...
}

UEContextModificationFailureIEs F1AP-PROTOCOL-IES ::= {
	{ ID id-gNB-CU-UE-F1AP-ID				CRITICALITY reject	TYPE GNB-CU-UE-F1AP-ID				PRESENCE mandatory	}|
	{ ID id-gNB-DU-UE-F1AP-ID				CRITICALITY reject	TYPE GNB-DU-UE-F1AP-ID				PRESENCE mandatory	}|
	{ ID id-Cause							CRITICALITY ignore	TYPE Cause							PRESENCE mandatory	}|
	{ ID id-CriticalityDiagnostics			CRITICALITY ignore	TYPE CriticalityDiagnostics			PRESENCE optional	}|
	{ ID id-requestedTargetCellGlobalID		CRITICALITY reject	TYPE NRCGI							PRESENCE optional},
	...
}


-- **************************************************************
--
-- UE Context Modification Required (gNB-DU initiated) ELEMENTARY PROCEDURE
--
-- **************************************************************

-- **************************************************************
--
-- UE CONTEXT MODIFICATION REQUIRED
--
-- **************************************************************

UEContextModificationRequired ::= SEQUENCE {
	protocolIEs			ProtocolIE-Container       { { UEContextModificationRequiredIEs} },
	...
}

UEContextModificationRequiredIEs F1AP-PROTOCOL-IES ::= {
	{ ID id-gNB-CU-UE-F1AP-ID							CRITICALITY reject	TYPE GNB-CU-UE-F1AP-ID									PRESENCE mandatory	}|
	{ ID id-gNB-DU-UE-F1AP-ID							CRITICALITY reject	TYPE GNB-DU-UE-F1AP-ID									PRESENCE mandatory	}|
	{ ID id-ResourceCoordinationTransferContainer		CRITICALITY ignore	TYPE ResourceCoordinationTransferContainer			PRESENCE optional	}|
	{ ID id-DUtoCURRCInformation						CRITICALITY reject	TYPE DUtoCURRCInformation								PRESENCE optional}|
	{ ID id-DRBs-Required-ToBeModified-List				CRITICALITY reject	TYPE DRBs-Required-ToBeModified-List					PRESENCE optional}|
	{ ID id-SRBs-Required-ToBeReleased-List				CRITICALITY reject	TYPE SRBs-Required-ToBeReleased-List					PRESENCE optional}|
	{ ID id-DRBs-Required-ToBeReleased-List				CRITICALITY reject	TYPE DRBs-Required-ToBeReleased-List					PRESENCE optional}|
	{ ID id-Cause										CRITICALITY ignore	TYPE Cause													PRESENCE mandatory	}|
	{ ID id-BHChannels-Required-ToBeReleased-List		CRITICALITY reject	TYPE BHChannels-Required-ToBeReleased-List			PRESENCE optional}|
	{ ID id-SLDRBs-Required-ToBeModified-List			CRITICALITY reject	TYPE SLDRBs-Required-ToBeModified-List				PRESENCE optional}|
	{ ID id-SLDRBs-Required-ToBeReleased-List			CRITICALITY reject	TYPE SLDRBs-Required-ToBeReleased-List				PRESENCE optional}|
	{ ID id-targetCellsToCancel							CRITICALITY reject	TYPE TargetCellList											PRESENCE optional}|
	{ ID id-UuRLCChannelRequiredToBeModifiedList		CRITICALITY reject	TYPE UuRLCChannelRequiredToBeModifiedList			PRESENCE optional}|
	{ ID id-UuRLCChannelRequiredToBeReleasedList		CRITICALITY reject	TYPE UuRLCChannelRequiredToBeReleasedList			PRESENCE optional}|
	{ ID id-PC5RLCChannelRequiredToBeModifiedList		CRITICALITY reject	TYPE PC5RLCChannelRequiredToBeModifiedList			PRESENCE optional}|
	{ ID id-PC5RLCChannelRequiredToBeReleasedList		CRITICALITY reject	TYPE PC5RLCChannelRequiredToBeReleasedList			PRESENCE optional}|
	{ ID id-UE-MulticastMRBs-RequiredToBeModified-List	CRITICALITY reject	TYPE UE-MulticastMRBs-RequiredToBeModified-List	PRESENCE optional  }|
	{ ID id-UE-MulticastMRBs-RequiredToBeReleased-List	CRITICALITY reject	TYPE UE-MulticastMRBs-RequiredToBeReleased-List	PRESENCE optional  }|
	{ ID id-LTMCells-ToBeReleased-List					CRITICALITY reject	TYPE LTMCells-ToBeReleased-List						PRESENCE optional	}|
	{ ID id-LTMConfig-to-Modify-List					CRITICALITY ignore	TYPE LTMConfig-to-Modify-List							PRESENCE optional	},
	...
}

DRBs-Required-ToBeModified-List::= SEQUENCE (SIZE(1..maxnoofDRBs)) OF ProtocolIE-SingleContainer { { DRBs-Required-ToBeModified-ItemIEs } }
DRBs-Required-ToBeReleased-List::= SEQUENCE (SIZE(1..maxnoofDRBs)) OF ProtocolIE-SingleContainer { { DRBs-Required-ToBeReleased-ItemIEs } }

SRBs-Required-ToBeReleased-List::= SEQUENCE (SIZE(1..maxnoofSRBs)) OF ProtocolIE-SingleContainer { { SRBs-Required-ToBeReleased-ItemIEs } }

BHChannels-Required-ToBeReleased-List ::= SEQUENCE (SIZE(1..maxnoofBHRLCChannels)) OF ProtocolIE-SingleContainer { { BHChannels-Required-ToBeReleased-ItemIEs } }

DRBs-Required-ToBeModified-ItemIEs F1AP-PROTOCOL-IES ::= {
	{ ID id-DRBs-Required-ToBeModified-Item			CRITICALITY reject	TYPE DRBs-Required-ToBeModified-Item		PRESENCE mandatory},
	...
}

DRBs-Required-ToBeReleased-ItemIEs F1AP-PROTOCOL-IES ::= {
	{ ID id-DRBs-Required-ToBeReleased-Item			CRITICALITY reject	TYPE DRBs-Required-ToBeReleased-Item		PRESENCE mandatory},
	...
}

SRBs-Required-ToBeReleased-ItemIEs F1AP-PROTOCOL-IES ::= {
	{ ID id-SRBs-Required-ToBeReleased-Item			CRITICALITY reject	TYPE SRBs-Required-ToBeReleased-Item			PRESENCE mandatory},
	...
}

BHChannels-Required-ToBeReleased-ItemIEs F1AP-PROTOCOL-IES ::= {
	{ ID id-BHChannels-Required-ToBeReleased-Item			CRITICALITY reject	TYPE BHChannels-Required-ToBeReleased-Item		PRESENCE mandatory},
	...
}

SLDRBs-Required-ToBeModified-List::= SEQUENCE (SIZE(1..maxnoofSLDRBs)) OF ProtocolIE-SingleContainer { { SLDRBs-Required-ToBeModified-ItemIEs } }
SLDRBs-Required-ToBeReleased-List::= SEQUENCE (SIZE(1..maxnoofSLDRBs)) OF ProtocolIE-SingleContainer { { SLDRBs-Required-ToBeReleased-ItemIEs } }

SLDRBs-Required-ToBeModified-ItemIEs F1AP-PROTOCOL-IES ::= {
	{ ID id-SLDRBs-Required-ToBeModified-Item			CRITICALITY reject	TYPE SLDRBs-Required-ToBeModified-Item		PRESENCE mandatory},
	...
}

SLDRBs-Required-ToBeReleased-ItemIEs F1AP-PROTOCOL-IES ::= {
	{ ID id-SLDRBs-Required-ToBeReleased-Item			CRITICALITY reject	TYPE SLDRBs-Required-ToBeReleased-Item		PRESENCE mandatory},
	...
}

UE-MulticastMRBs-RequiredToBeModified-List ::= SEQUENCE (SIZE(1..maxnoofMRBsforUE)) OF
							ProtocolIE-SingleContainer { { UE-MulticastMRBs-RequiredToBeModified-ItemIEs} }

UE-MulticastMRBs-RequiredToBeModified-ItemIEs F1AP-PROTOCOL-IES ::= {
	{ ID id-UE-MulticastMRBs-RequiredToBeModified-Item	CRITICALITY reject	TYPE UE-MulticastMRBs-RequiredToBeModified-Item		PRESENCE mandatory},
	...
}

UE-MulticastMRBs-RequiredToBeReleased-List ::= SEQUENCE (SIZE(1..maxnoofMRBsforUE)) OF
							ProtocolIE-SingleContainer { { UE-MulticastMRBs-RequiredToBeReleased-ItemIEs} }

UE-MulticastMRBs-RequiredToBeReleased-ItemIEs F1AP-PROTOCOL-IES ::= {
	{ ID id-UE-MulticastMRBs-RequiredToBeReleased-Item		CRITICALITY reject	TYPE UE-MulticastMRBs-RequiredToBeReleased-Item		PRESENCE mandatory},
	...
}


-- **************************************************************
--
-- UE CONTEXT MODIFICATION CONFIRM
--
-- **************************************************************

UEContextModificationConfirm::= SEQUENCE {
	protocolIEs			ProtocolIE-Container       { { UEContextModificationConfirmIEs} },
	...
}


UEContextModificationConfirmIEs F1AP-PROTOCOL-IES ::= {
	{ ID id-gNB-CU-UE-F1AP-ID							CRITICALITY reject	TYPE GNB-CU-UE-F1AP-ID									PRESENCE mandatory	}|
	{ ID id-gNB-DU-UE-F1AP-ID							CRITICALITY reject	TYPE GNB-DU-UE-F1AP-ID									PRESENCE mandatory	}|
	{ ID id-ResourceCoordinationTransferContainer		CRITICALITY ignore	TYPE ResourceCoordinationTransferContainer			PRESENCE optional		}|
	{ ID id-DRBs-ModifiedConf-List						CRITICALITY ignore	TYPE DRBs-ModifiedConf-List								PRESENCE optional		}|
	{ ID id-RRCContainer								CRITICALITY ignore	TYPE RRCContainer											PRESENCE optional		}|
	{ ID id-CriticalityDiagnostics						CRITICALITY ignore	TYPE CriticalityDiagnostics								PRESENCE optional		}|
	{ ID id-ExecuteDuplication							CRITICALITY ignore	TYPE ExecuteDuplication									PRESENCE optional		}|
	{ ID id-ResourceCoordinationTransferInformation		CRITICALITY ignore	TYPE ResourceCoordinationTransferInformation		PRESENCE optional		}|
	{ ID id-SLDRBs-ModifiedConf-List					CRITICALITY ignore	TYPE SLDRBs-ModifiedConf-List							PRESENCE optional		}|
	{ ID id-UuRLCChannelModifiedList					CRITICALITY reject	TYPE UuRLCChannelModifiedList							PRESENCE optional		}|
	{ ID id-PC5RLCChannelModifiedList					CRITICALITY reject	TYPE PC5RLCChannelModifiedList							PRESENCE optional		}|
	{ ID id-UE-MulticastMRBs-ConfirmedToBeModified-List	CRITICALITY reject	TYPE UE-MulticastMRBs-ConfirmedToBeModified-List	PRESENCE optional		},
	...
}

DRBs-ModifiedConf-List::= SEQUENCE (SIZE(1..maxnoofDRBs)) OF ProtocolIE-SingleContainer { { DRBs-ModifiedConf-ItemIEs } }

DRBs-ModifiedConf-ItemIEs F1AP-PROTOCOL-IES ::= {
	{ ID id-DRBs-ModifiedConf-Item		CRITICALITY ignore	TYPE DRBs-ModifiedConf-Item			PRESENCE mandatory},
	...
}

SLDRBs-ModifiedConf-List::= SEQUENCE (SIZE(1..maxnoofSLDRBs)) OF ProtocolIE-SingleContainer { { SLDRBs-ModifiedConf-ItemIEs } }

SLDRBs-ModifiedConf-ItemIEs F1AP-PROTOCOL-IES ::= {
	{ ID id-SLDRBs-ModifiedConf-Item		CRITICALITY ignore	TYPE SLDRBs-ModifiedConf-Item			PRESENCE mandatory},
	...
}

UE-MulticastMRBs-ConfirmedToBeModified-List ::= SEQUENCE (SIZE(1..maxnoofMRBsforUE)) OF
							ProtocolIE-SingleContainer { { UE-MulticastMRBs-ConfirmedToBeModified-ItemIEs} }

UE-MulticastMRBs-ConfirmedToBeModified-ItemIEs F1AP-PROTOCOL-IES ::= {
	{ ID id-UE-MulticastMRBs-ConfirmedToBeModified-Item	CRITICALITY reject	TYPE UE-MulticastMRBs-ConfirmedToBeModified-Item		PRESENCE mandatory},
	...
}


-- **************************************************************
--
-- UE CONTEXT MODIFICATION REFUSE
--
-- **************************************************************

UEContextModificationRefuse::= SEQUENCE {
	protocolIEs			ProtocolIE-Container       { { UEContextModificationRefuseIEs} },
	...
}


UEContextModificationRefuseIEs F1AP-PROTOCOL-IES ::= {
	{ ID id-gNB-CU-UE-F1AP-ID				CRITICALITY reject	TYPE GNB-CU-UE-F1AP-ID				PRESENCE mandatory	}|
	{ ID id-gNB-DU-UE-F1AP-ID				CRITICALITY reject	TYPE GNB-DU-UE-F1AP-ID				PRESENCE mandatory	}|
	{ ID id-Cause							CRITICALITY ignore	TYPE Cause							PRESENCE mandatory	}|
	{ ID id-CriticalityDiagnostics			CRITICALITY ignore	TYPE CriticalityDiagnostics			PRESENCE optional	},
	...
}


-- **************************************************************
--
-- WRITE-REPLACE WARNING ELEMENTARY PROCEDURE
--
-- **************************************************************

-- **************************************************************
--
-- Write-Replace Warning Request
--
-- **************************************************************

WriteReplaceWarningRequest ::= SEQUENCE {
	protocolIEs ProtocolIE-Container { {WriteReplaceWarningRequestIEs} },
	...
}

WriteReplaceWarningRequestIEs F1AP-PROTOCOL-IES ::= {
	{ ID id-TransactionID						CRITICALITY reject	TYPE TransactionID								PRESENCE mandatory	}|
	{ ID id-PWSSystemInformation 				CRITICALITY reject	TYPE PWSSystemInformation 						PRESENCE mandatory }|
	{ ID id-RepetitionPeriod 					CRITICALITY reject	TYPE RepetitionPeriod 							PRESENCE mandatory }|
	{ ID id-NumberofBroadcastRequest 			CRITICALITY reject	TYPE NumberofBroadcastRequest 				PRESENCE mandatory }|
	{ ID id-Cells-To-Be-Broadcast-List			CRITICALITY reject	TYPE Cells-To-Be-Broadcast-List				PRESENCE optional	},
	...
}

Cells-To-Be-Broadcast-List		::= SEQUENCE (SIZE(1.. maxCellingNBDU))	OF ProtocolIE-SingleContainer { { Cells-To-Be-Broadcast-List-ItemIEs } }

Cells-To-Be-Broadcast-List-ItemIEs F1AP-PROTOCOL-IES	::= {
	{ ID id-Cells-To-Be-Broadcast-Item		CRITICALITY reject	TYPE	Cells-To-Be-Broadcast-Item		PRESENCE mandatory	},
	...
}

-- **************************************************************
--
-- Write-Replace Warning Response
--
-- **************************************************************

WriteReplaceWarningResponse ::= SEQUENCE {
	protocolIEs ProtocolIE-Container { {WriteReplaceWarningResponseIEs} },
	...
}

WriteReplaceWarningResponseIEs F1AP-PROTOCOL-IES ::= {
	{ ID id-TransactionID							CRITICALITY reject	TYPE TransactionID										PRESENCE mandatory	}|
	{ ID id-Cells-Broadcast-Completed-List			CRITICALITY reject	TYPE Cells-Broadcast-Completed-List				PRESENCE optional	}|
	{ ID id-CriticalityDiagnostics					CRITICALITY ignore	TYPE CriticalityDiagnostics							PRESENCE optional	}|
	{ ID id-Dedicated-SIDelivery-NeededUE-List		CRITICALITY ignore	TYPE Dedicated-SIDelivery-NeededUE-List			PRESENCE optional	},
	...
}

Cells-Broadcast-Completed-List		::= SEQUENCE (SIZE(1.. maxCellingNBDU))	OF ProtocolIE-SingleContainer { { Cells-Broadcast-Completed-List-ItemIEs } }

Cells-Broadcast-Completed-List-ItemIEs F1AP-PROTOCOL-IES	::= {
	{ ID id-Cells-Broadcast-Completed-Item		CRITICALITY reject	TYPE	Cells-Broadcast-Completed-Item		PRESENCE mandatory	},
	...
}


-- **************************************************************
--
-- PWS CANCEL ELEMENTARY PROCEDURE
--
-- **************************************************************

-- **************************************************************
--
-- PWS Cancel Request
--
-- **************************************************************

PWSCancelRequest ::= SEQUENCE {
	protocolIEs ProtocolIE-Container { {PWSCancelRequestIEs} },
	...
}

PWSCancelRequestIEs F1AP-PROTOCOL-IES ::= {
	{ ID id-TransactionID							CRITICALITY reject TYPE TransactionID									PRESENCE mandatory	}|
	{ ID id-NumberofBroadcastRequest 				CRITICALITY reject TYPE NumberofBroadcastRequest						PRESENCE mandatory }|
	{ ID id-Broadcast-To-Be-Cancelled-List			CRITICALITY reject TYPE Broadcast-To-Be-Cancelled-List				PRESENCE optional	}|
	{ ID id-Cancel-all-Warning-Messages-Indicator	CRITICALITY reject TYPE Cancel-all-Warning-Messages-Indicator	PRESENCE optional	}|
	{ ID id-NotificationInformation					CRITICALITY reject TYPE NotificationInformation						PRESENCE optional},
	...
}

Broadcast-To-Be-Cancelled-List		::= SEQUENCE (SIZE(1.. maxCellingNBDU))	OF ProtocolIE-SingleContainer { { Broadcast-To-Be-Cancelled-List-ItemIEs } }

Broadcast-To-Be-Cancelled-List-ItemIEs F1AP-PROTOCOL-IES	::= {
	{ ID id-Broadcast-To-Be-Cancelled-Item		CRITICALITY reject	TYPE	Broadcast-To-Be-Cancelled-Item		PRESENCE mandatory	},
	...
}

-- **************************************************************
--
-- PWS Cancel Response
--
-- **************************************************************

PWSCancelResponse ::= SEQUENCE {
	protocolIEs ProtocolIE-Container { {PWSCancelResponseIEs} },
	...
}

PWSCancelResponseIEs F1AP-PROTOCOL-IES ::= {
	{ ID id-TransactionID					CRITICALITY reject	TYPE TransactionID						PRESENCE mandatory	}|
	{ ID id-Cells-Broadcast-Cancelled-List	CRITICALITY reject	TYPE Cells-Broadcast-Cancelled-List	PRESENCE optional	}|
	{ ID id-CriticalityDiagnostics			CRITICALITY ignore	TYPE CriticalityDiagnostics				PRESENCE optional	},
	...
}

Cells-Broadcast-Cancelled-List		::= SEQUENCE (SIZE(1.. maxCellingNBDU))	OF ProtocolIE-SingleContainer { { Cells-Broadcast-Cancelled-List-ItemIEs } }

Cells-Broadcast-Cancelled-List-ItemIEs F1AP-PROTOCOL-IES	::= {
	{ ID id-Cells-Broadcast-Cancelled-Item		CRITICALITY reject	TYPE	Cells-Broadcast-Cancelled-Item		PRESENCE mandatory	},
	...
}

-- **************************************************************
--
-- UE Inactivity Notification ELEMENTARY PROCEDURE
--
-- **************************************************************

-- **************************************************************
--
-- UE Inactivity Notification
--
-- **************************************************************

UEInactivityNotification ::= SEQUENCE {
	protocolIEs			ProtocolIE-Container       {{ UEInactivityNotificationIEs}},
	...
}

UEInactivityNotificationIEs F1AP-PROTOCOL-IES ::= {
	{ ID id-gNB-CU-UE-F1AP-ID							CRITICALITY reject	TYPE GNB-CU-UE-F1AP-ID							PRESENCE mandatory	}|
	{ ID id-gNB-DU-UE-F1AP-ID							CRITICALITY reject	TYPE GNB-DU-UE-F1AP-ID							PRESENCE mandatory	}|
	{ ID id-DRB-Activity-List							CRITICALITY reject	TYPE DRB-Activity-List							PRESENCE mandatory	}|
	{ ID id-SDT-Termination-Request						CRITICALITY ignore	TYPE SDT-Termination-Request					PRESENCE optional 	},
	...
}

DRB-Activity-List::= SEQUENCE (SIZE(1..maxnoofDRBs)) OF ProtocolIE-SingleContainer { { DRB-Activity-ItemIEs } }

DRB-Activity-ItemIEs F1AP-PROTOCOL-IES ::= {
	{ ID id-DRB-Activity-Item			CRITICALITY reject	TYPE DRB-Activity-Item		PRESENCE mandatory},
	...
}
-- **************************************************************
--
-- Initial UL RRC Message Transfer ELEMENTARY PROCEDURE
--
-- **************************************************************

-- **************************************************************
--
-- INITIAL UL RRC Message Transfer
--
-- **************************************************************

InitialULRRCMessageTransfer ::= SEQUENCE {
	protocolIEs			ProtocolIE-Container       {{ InitialULRRCMessageTransferIEs}},
	...
}

InitialULRRCMessageTransferIEs F1AP-PROTOCOL-IES ::= {
	{ ID id-gNB-DU-UE-F1AP-ID					CRITICALITY reject	TYPE GNB-DU-UE-F1AP-ID						PRESENCE mandatory	}|
	{ ID id-NRCGI								CRITICALITY reject	TYPE NRCGI									PRESENCE mandatory	}|
	{ ID id-C-RNTI								CRITICALITY reject	TYPE C-RNTI									PRESENCE mandatory	}|
	{ ID id-RRCContainer						CRITICALITY reject	TYPE RRCContainer							PRESENCE mandatory	}|
	{ ID id-DUtoCURRCContainer					CRITICALITY reject	TYPE DUtoCURRCContainer						PRESENCE optional	}|
	{ ID id-SULAccessIndication					CRITICALITY ignore	TYPE SULAccessIndication					PRESENCE optional	}|
	{ ID id-TransactionID						CRITICALITY ignore	TYPE TransactionID							PRESENCE mandatory	}|
	{ ID id-RANUEID								CRITICALITY ignore	TYPE RANUEID								PRESENCE optional	}|
	{ ID id-RRCContainer-RRCSetupComplete		CRITICALITY ignore	TYPE RRCContainer-RRCSetupComplete 			PRESENCE optional	}|
	{ ID id-NRRedCapUEIndication				CRITICALITY ignore	TYPE NRRedCapUEIndication  					PRESENCE optional	}|
	{ ID id-SDTInformation						CRITICALITY ignore	TYPE SDTInformation							PRESENCE optional	}|
	{ ID id-SidelinkRelayConfiguration			CRITICALITY ignore	TYPE SidelinkRelayConfiguration			PRESENCE optional	}|
{ ID id-NReRedCapUEIndication					CRITICALITY ignore	TYPE NReRedCapUEIndication  				PRESENCE optional	},
	...
}


-- **************************************************************
--
-- DL RRC Message Transfer ELEMENTARY PROCEDURE
--
-- **************************************************************

-- **************************************************************
--
-- DL RRC Message Transfer
--
-- **************************************************************

DLRRCMessageTransfer ::= SEQUENCE {
	protocolIEs			ProtocolIE-Container       {{ DLRRCMessageTransferIEs}},
	...
}

DLRRCMessageTransferIEs F1AP-PROTOCOL-IES ::= {
	{ ID id-gNB-CU-UE-F1AP-ID							CRITICALITY reject	TYPE GNB-CU-UE-F1AP-ID							PRESENCE mandatory	}|
	{ ID id-gNB-DU-UE-F1AP-ID							CRITICALITY reject	TYPE GNB-DU-UE-F1AP-ID							PRESENCE mandatory	}|
	{ ID id-oldgNB-DU-UE-F1AP-ID						CRITICALITY reject	TYPE GNB-DU-UE-F1AP-ID							PRESENCE optional	}|
	{ ID id-SRBID										CRITICALITY reject	TYPE SRBID											PRESENCE mandatory	}|
	{ ID id-ExecuteDuplication							CRITICALITY ignore	TYPE ExecuteDuplication							PRESENCE optional}|
	{ ID id-RRCContainer								CRITICALITY reject	TYPE RRCContainer									PRESENCE mandatory	}|
	{ ID id-RAT-FrequencyPriorityInformation			CRITICALITY reject	TYPE RAT-FrequencyPriorityInformation		PRESENCE optional	}|
	{ ID id-RRCDeliveryStatusRequest					CRITICALITY ignore	TYPE RRCDeliveryStatusRequest					PRESENCE optional }|
	{ ID id-UEContextNotRetrievable						CRITICALITY reject	TYPE UEContextNotRetrievable					PRESENCE optional }|
	{ ID id-RedirectedRRCmessage						CRITICALITY reject	TYPE OCTET STRING									PRESENCE optional }|
	{ ID id-PLMNAssistanceInfoForNetShar				CRITICALITY ignore	TYPE PLMN-Identity									PRESENCE optional }|
	{ ID id-new-gNB-CU-UE-F1AP-ID						CRITICALITY reject	TYPE GNB-CU-UE-F1AP-ID							PRESENCE optional }|
	{ ID id-AdditionalRRMPriorityIndex					CRITICALITY ignore	TYPE AdditionalRRMPriorityIndex				PRESENCE optional }|
	{ ID id-SRBMappingInfo								CRITICALITY ignore	TYPE UuRLCChannelID					 				PRESENCE optional }|
	{ ID id-PLMNIndexNRAssistanceInfoForNetShar					CRITICALITY ignore	TYPE PLMNIndexNR											PRESENCE optional }|
	{ ID id-AreaSpecificSemiPersistentSRSPosInfo		CRITICALITY ignore	TYPE AreaSpecificSemiPersistentSRSPosInfo 	PRESENCE optional },
	...
}
-- **************************************************************
--
-- UL RRC Message Transfer ELEMENTARY PROCEDURE
--
-- **************************************************************

-- **************************************************************
--
-- UL RRC Message Transfer
--
-- **************************************************************

ULRRCMessageTransfer ::= SEQUENCE {
	protocolIEs			ProtocolIE-Container       {{ ULRRCMessageTransferIEs}},
	...
}

ULRRCMessageTransferIEs F1AP-PROTOCOL-IES ::= {
	{ ID id-gNB-CU-UE-F1AP-ID				CRITICALITY reject	TYPE GNB-CU-UE-F1AP-ID				PRESENCE mandatory	}|
	{ ID id-gNB-DU-UE-F1AP-ID				CRITICALITY reject	TYPE GNB-DU-UE-F1AP-ID				PRESENCE mandatory	}|
	{ ID id-SRBID							CRITICALITY reject	TYPE SRBID							PRESENCE mandatory	}|
	{ ID id-RRCContainer					CRITICALITY reject	TYPE RRCContainer					PRESENCE mandatory	}|
	{ ID id-SelectedPLMNID					CRITICALITY reject	TYPE PLMN-Identity					PRESENCE optional		}|
	{ ID id-new-gNB-DU-UE-F1AP-ID			CRITICALITY reject	TYPE GNB-DU-UE-F1AP-ID				PRESENCE optional		},
	...
}

-- **************************************************************
--
-- PRIVATE MESSAGE
--
-- **************************************************************

PrivateMessage ::= SEQUENCE {
	privateIEs		PrivateIE-Container	{{PrivateMessage-IEs}},
	...
}

PrivateMessage-IEs F1AP-PRIVATE-IES ::= {
	...
}


-- **************************************************************
--
-- System Information ELEMENTARY PROCEDURE
--
-- **************************************************************

-- **************************************************************
--
-- System information Delivery Command
--
-- **************************************************************

SystemInformationDeliveryCommand ::= SEQUENCE {
	protocolIEs			ProtocolIE-Container       {{ SystemInformationDeliveryCommandIEs}},
	...
}

SystemInformationDeliveryCommandIEs F1AP-PROTOCOL-IES ::= {
	{ ID id-TransactionID			CRITICALITY reject	TYPE TransactionID					PRESENCE mandatory	}|
	{ ID id-NRCGI					CRITICALITY reject	TYPE NRCGI							PRESENCE mandatory	}|
	{ ID id-SItype-List				CRITICALITY reject	TYPE SItype-List					PRESENCE mandatory	}|
	{ ID id-ConfirmedUEID 			CRITICALITY reject	TYPE GNB-DU-UE-F1AP-ID				PRESENCE mandatory	},
	...
}


-- **************************************************************
--
-- Paging PROCEDURE
--
-- **************************************************************

-- **************************************************************
--
-- Paging
--
-- **************************************************************

Paging ::= SEQUENCE {
	protocolIEs			ProtocolIE-Container       {{ PagingIEs}},
	...
}

PagingIEs F1AP-PROTOCOL-IES ::= {
	{ ID id-UEIdentityIndexValue	CRITICALITY reject	TYPE UEIdentityIndexValue		PRESENCE mandatory	}|
	{ ID id-PagingIdentity			CRITICALITY reject	TYPE PagingIdentity				PRESENCE mandatory	}|
	{ ID id-PagingDRX				CRITICALITY ignore	TYPE PagingDRX					PRESENCE optional	}|
	{ ID id-PagingPriority			CRITICALITY ignore	TYPE PagingPriority				PRESENCE optional	}|
	{ ID id-PagingCell-List			CRITICALITY ignore	TYPE PagingCell-list			PRESENCE mandatory	}|
	{ ID id-PagingOrigin			CRITICALITY ignore	TYPE PagingOrigin				PRESENCE optional	}|
	{ ID id-RANUEPagingDRX			CRITICALITY ignore	TYPE PagingDRX					PRESENCE optional	}|
	{ ID id-CNUEPagingDRX			CRITICALITY ignore	TYPE PagingDRX					PRESENCE optional	}|
	{ ID id-NRPagingeDRXInformation	CRITICALITY ignore	TYPE NRPagingeDRXInformation	PRESENCE optional	}|
	{ ID id-NRPagingeDRXInformationforRRCINACTIVE	CRITICALITY ignore	TYPE NRPagingeDRXInformationforRRCINACTIVE	PRESENCE optional	}|
	{ ID id-PagingCause			CRITICALITY ignore	TYPE PagingCause				PRESENCE optional	}|
	{ ID id-PEIPSAssistanceInfo		CRITICALITY ignore	TYPE PEIPSAssistanceInfo		PRESENCE optional	}|
	{ ID id-UEPagingCapability		CRITICALITY ignore	TYPE UEPagingCapability			PRESENCE optional	}|
	{ ID id-ExtendedUEIdentityIndexValue	CRITICALITY ignore	TYPE ExtendedUEIdentityIndexValue		PRESENCE optional}|
	{ ID id-HashedUEIdentityIndexValue		CRITICALITY ignore	TYPE HashedUEIdentityIndexValue			PRESENCE optional}|
	{ ID id-MT-SDT-Information		CRITICALITY ignore	TYPE MT-SDT-Information			PRESENCE optional	}|
	{ ID id-NRPaginglongeDRXInformationforRRCINACTIVE		CRITICALITY ignore		TYPE NRPaginglongeDRXInformationforRRCINACTIVE				PRESENCE optional }|
	{ ID id-LPWUSPSAssistanceInfo	CRITICALITY ignore	TYPE LPWUSPSAssistanceInfo		PRESENCE optional	}|
	{ ID id-FurtherExtendedUEIdentityIndexValue	CRITICALITY ignore	TYPE FurtherExtendedUEIdentityIndexValue		PRESENCE optional	},
	...
}

PagingCell-list::= SEQUENCE (SIZE(1.. maxnoofPagingCells)) OF ProtocolIE-SingleContainer { { PagingCell-ItemIEs } }

PagingCell-ItemIEs F1AP-PROTOCOL-IES ::= {
	{ ID id-PagingCell-Item		CRITICALITY ignore	TYPE PagingCell-Item			PRESENCE mandatory}	,
	...
}



-- **************************************************************
--
-- Notify
--
-- **************************************************************

Notify ::= SEQUENCE {
	protocolIEs			ProtocolIE-Container       {{ NotifyIEs}},
	...
}

NotifyIEs F1AP-PROTOCOL-IES ::= {
	{ ID id-gNB-CU-UE-F1AP-ID					CRITICALITY reject	TYPE GNB-CU-UE-F1AP-ID						PRESENCE mandatory	}|
	{ ID id-gNB-DU-UE-F1AP-ID					CRITICALITY reject	TYPE GNB-DU-UE-F1AP-ID						PRESENCE mandatory	}|
	{ ID id-DRB-Notify-List						CRITICALITY reject	TYPE DRB-Notify-List						PRESENCE mandatory	},
	...
}

DRB-Notify-List::= SEQUENCE (SIZE(1.. maxnoofDRBs)) OF ProtocolIE-SingleContainer { { DRB-Notify-ItemIEs } }

DRB-Notify-ItemIEs F1AP-PROTOCOL-IES ::= {
	{ ID id-DRB-Notify-Item			CRITICALITY reject	TYPE DRB-Notify-Item		PRESENCE mandatory},
	...
}


-- **************************************************************
--
-- NETWORK ACCESS RATE REDUCTION ELEMENTARY PROCEDURE
--
-- **************************************************************

-- **************************************************************
--
-- Network Access Rate Reduction
--
-- **************************************************************

NetworkAccessRateReduction ::= SEQUENCE {
	protocolIEs			ProtocolIE-Container       {{ NetworkAccessRateReductionIEs }},
	...
}

NetworkAccessRateReductionIEs F1AP-PROTOCOL-IES ::= {
	{ ID id-TransactionID 					CRITICALITY reject	TYPE TransactionID					PRESENCE mandatory	}|
	{ ID id-UAC-Assistance-Info				CRITICALITY reject	TYPE UAC-Assistance-Info			PRESENCE mandatory	},
	...
}

-- **************************************************************
--
-- PWS RESTART INDICATION ELEMENTARY PROCEDURE
--
-- **************************************************************

-- **************************************************************
--
-- PWS Restart Indication
--
-- **************************************************************

PWSRestartIndication ::= SEQUENCE {
	protocolIEs ProtocolIE-Container { { PWSRestartIndicationIEs} },
	...
}

PWSRestartIndicationIEs F1AP-PROTOCOL-IES ::= {
	{ ID id-TransactionID					CRITICALITY reject	TYPE TransactionID					PRESENCE mandatory	}|
	{ ID id-NR-CGI-List-For-Restart-List	CRITICALITY reject	TYPE NR-CGI-List-For-Restart-List	PRESENCE mandatory	},
	...
}

NR-CGI-List-For-Restart-List		::= SEQUENCE (SIZE(1.. maxCellingNBDU))	OF ProtocolIE-SingleContainer { { NR-CGI-List-For-Restart-List-ItemIEs } }

NR-CGI-List-For-Restart-List-ItemIEs F1AP-PROTOCOL-IES	::= {
	{ ID id-NR-CGI-List-For-Restart-Item		CRITICALITY reject	TYPE	NR-CGI-List-For-Restart-Item		PRESENCE mandatory	},
	...
}

-- **************************************************************
--
-- PWS FAILURE INDICATION ELEMENTARY PROCEDURE
--
-- **************************************************************

-- **************************************************************
--
-- PWS Failure Indication
--
-- **************************************************************

PWSFailureIndication ::= SEQUENCE {
	protocolIEs ProtocolIE-Container { { PWSFailureIndicationIEs} },
	...
}

PWSFailureIndicationIEs F1AP-PROTOCOL-IES ::= {
	{ ID id-TransactionID			CRITICALITY reject	TYPE TransactionID				PRESENCE mandatory	}|
	{ ID id-PWS-Failed-NR-CGI-List	CRITICALITY reject	TYPE PWS-Failed-NR-CGI-List		PRESENCE optional	},
	...
}

PWS-Failed-NR-CGI-List		::= SEQUENCE (SIZE(1.. maxCellingNBDU))	OF ProtocolIE-SingleContainer { { PWS-Failed-NR-CGI-List-ItemIEs } }

PWS-Failed-NR-CGI-List-ItemIEs F1AP-PROTOCOL-IES	::= {
	{ ID id-PWS-Failed-NR-CGI-Item		CRITICALITY reject	TYPE	PWS-Failed-NR-CGI-Item		PRESENCE mandatory	},
	...
}


-- **************************************************************
--
-- gNB-DU STATUS INDICATION ELEMENTARY PROCEDURE
--
-- **************************************************************

-- **************************************************************
--
-- gNB-DU Status Indication
--
-- **************************************************************

GNBDUStatusIndication ::= SEQUENCE {
	protocolIEs			ProtocolIE-Container       { {GNBDUStatusIndicationIEs} },
	...
}

GNBDUStatusIndicationIEs F1AP-PROTOCOL-IES ::= {
	{ ID id-TransactionID					CRITICALITY reject	TYPE TransactionID					PRESENCE mandatory	}|
	{ ID id-GNBDUOverloadInformation		CRITICALITY reject	TYPE GNBDUOverloadInformation		PRESENCE mandatory	}|
	{ ID id-IABCongestionIndication			CRITICALITY ignore	TYPE IABCongestionIndication		PRESENCE optional		},
	...
}



-- **************************************************************
--
-- RRC Delivery Report ELEMENTARY PROCEDURE
--
-- **************************************************************

-- **************************************************************
--
-- RRC Delivery Report
--
-- **************************************************************

RRCDeliveryReport ::= SEQUENCE {
	protocolIEs			ProtocolIE-Container       {{ RRCDeliveryReportIEs}},
	...
}

RRCDeliveryReportIEs F1AP-PROTOCOL-IES ::= {
	{ ID id-gNB-CU-UE-F1AP-ID	CRITICALITY reject	TYPE GNB-CU-UE-F1AP-ID	PRESENCE mandatory	}|
	{ ID id-gNB-DU-UE-F1AP-ID	CRITICALITY reject	TYPE GNB-DU-UE-F1AP-ID	PRESENCE mandatory	}|
	{ ID id-RRCDeliveryStatus	CRITICALITY ignore	TYPE RRCDeliveryStatus	PRESENCE mandatory	}|
	{ ID id-SRBID				CRITICALITY ignore	TYPE SRBID				PRESENCE mandatory	},
	...
}

-- **************************************************************
--
-- F1 Removal ELEMENTARY PROCEDURE
--
-- **************************************************************

-- **************************************************************
--
-- F1 Removal Request
--
-- **************************************************************

F1RemovalRequest ::= SEQUENCE {
	protocolIEs			ProtocolIE-Container       {{ F1RemovalRequestIEs }},
	...
}

F1RemovalRequestIEs F1AP-PROTOCOL-IES ::= {
	{ ID id-TransactionID			CRITICALITY reject	TYPE TransactionID					PRESENCE mandatory	},
	...
}

-- **************************************************************
--
-- F1 Removal Response
--
-- **************************************************************

F1RemovalResponse ::= SEQUENCE {
	protocolIEs			ProtocolIE-Container       {{ F1RemovalResponseIEs }},
	...
}

F1RemovalResponseIEs F1AP-PROTOCOL-IES ::= {
	{ ID id-TransactionID				CRITICALITY reject	TYPE TransactionID					PRESENCE mandatory	}|
	{ ID id-CriticalityDiagnostics		CRITICALITY ignore	TYPE CriticalityDiagnostics			PRESENCE optional	},

	...
}

-- **************************************************************
--
-- F1 Removal Failure
--
-- **************************************************************

F1RemovalFailure ::= SEQUENCE {
	protocolIEs			ProtocolIE-Container       {{ F1RemovalFailureIEs }},
	...
}

F1RemovalFailureIEs F1AP-PROTOCOL-IES ::= {
	{ ID id-TransactionID				CRITICALITY reject	TYPE TransactionID					PRESENCE mandatory	}|
	{ ID id-Cause						CRITICALITY ignore	TYPE Cause							PRESENCE mandatory	}|
	{ ID id-CriticalityDiagnostics		CRITICALITY ignore	TYPE CriticalityDiagnostics			PRESENCE optional	},

	...
}


-- **************************************************************
--
-- TRACE ELEMENTARY PROCEDURES
--
-- **************************************************************

-- **************************************************************
--
-- TRACE START
--
-- **************************************************************

TraceStart ::= SEQUENCE {
	protocolIEs		ProtocolIE-Container		{ {TraceStartIEs} },
	...
}

TraceStartIEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-TraceActivation				CRITICALITY ignore	TYPE TraceActivation				PRESENCE mandatory	},
	...
}

-- **************************************************************
--
-- DEACTIVATE TRACE
--
-- **************************************************************

DeactivateTrace ::= SEQUENCE {
	protocolIEs		ProtocolIE-Container		{ {DeactivateTraceIEs} },
	...
}

DeactivateTraceIEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-TraceID						CRITICALITY ignore	TYPE TraceID						PRESENCE mandatory	},
	...
}

-- **************************************************************
--
-- CELL TRAFFIC TRACE
--
-- **************************************************************

CellTrafficTrace ::= SEQUENCE {
	protocolIEs		ProtocolIE-Container		{ {CellTrafficTraceIEs} },
	...
}

CellTrafficTraceIEs F1AP-PROTOCOL-IES ::= {
	{ ID id-gNB-CU-UE-F1AP-ID				CRITICALITY reject	TYPE GNB-CU-UE-F1AP-ID				PRESENCE mandatory	}|
	{ ID id-gNB-DU-UE-F1AP-ID				CRITICALITY reject	TYPE GNB-DU-UE-F1AP-ID				PRESENCE mandatory	}|
	{ID id-TraceID							CRITICALITY ignore	TYPE TraceID						PRESENCE mandatory	}|
	{ID id-TraceCollectionEntityIPAddress	CRITICALITY ignore	TYPE TransportLayerAddress			PRESENCE mandatory	}|
	{ID id-PrivacyIndicator					CRITICALITY ignore	TYPE PrivacyIndicator				PRESENCE optional	}|
	{ID id-TraceCollectionEntityURI	CRITICALITY ignore	TYPE URI-address		PRESENCE optional	},
	...
}

-- **************************************************************
--
-- DU-CU Radio Information Transfer ELEMENTARY PROCEDURE
--
-- **************************************************************

-- **************************************************************
--
-- DU-CU Radio Information Transfer
--
-- **************************************************************

DUCURadioInformationTransfer ::= SEQUENCE {
	protocolIEs			ProtocolIE-Container       {{ DUCURadioInformationTransferIEs}},
	...
}

DUCURadioInformationTransferIEs F1AP-PROTOCOL-IES ::= {
	{ ID id-TransactionID					CRITICALITY reject	TYPE TransactionID						PRESENCE mandatory	}|
	{ ID id-DUCURadioInformationType		CRITICALITY ignore	TYPE DUCURadioInformationType				PRESENCE mandatory	},
	...
}



-- **************************************************************
--
-- CU-DU Radio Information Transfer ELEMENTARY PROCEDURE
--
-- **************************************************************

-- **************************************************************
--
-- CU-DU Radio Information Transfer
--
-- **************************************************************

CUDURadioInformationTransfer ::= SEQUENCE {
	protocolIEs			ProtocolIE-Container       {{ CUDURadioInformationTransferIEs}},
	...
}

CUDURadioInformationTransferIEs F1AP-PROTOCOL-IES ::= {
	{ ID id-TransactionID					CRITICALITY reject	TYPE TransactionID						PRESENCE mandatory	}|
	{ ID id-CUDURadioInformationType	CRITICALITY ignore	TYPE CUDURadioInformationType				PRESENCE mandatory	},
	...
}

-- **************************************************************
--
-- IAB PROCEDURES
--
-- **************************************************************
-- **************************************************************
--
-- BAP Mapping Configuration ELEMENTARY PROCEDURE
--
-- **************************************************************

-- **************************************************************
--
-- BAP MAPPING CONFIGURATION
--
-- **************************************************************


BAPMappingConfiguration ::= SEQUENCE {
	protocolIEs			ProtocolIE-Container	{ {BAPMappingConfiguration-IEs} },
	...
 }

BAPMappingConfiguration-IEs F1AP-PROTOCOL-IES ::= {
	{ ID id-TransactionID							CRITICALITY reject	TYPE	TransactionID								PRESENCE mandatory}|
	{ ID id-BH-Routing-Information-Added-List		CRITICALITY ignore	TYPE	BH-Routing-Information-Added-List	PRESENCE optional}|
	{ ID id-BH-Routing-Information-Removed-List		CRITICALITY ignore	TYPE	BH-Routing-Information-Removed-List	PRESENCE optional}|
	{ ID id-TrafficMappingInformation				CRITICALITY ignore	TYPE	TrafficMappingInfo						PRESENCE optional}|
	{ ID id-BufferSizeThresh						CRITICALITY ignore	TYPE	BufferSizeThresh							PRESENCE optional}|
	{ ID id-BAP-Header-Rewriting-Added-List			CRITICALITY ignore	TYPE	BAP-Header-Rewriting-Added-List		PRESENCE optional}|
	{ ID id-Re-routingEnableIndicator				CRITICALITY ignore	TYPE	Re-routingEnableIndicator				PRESENCE optional}|
	{ ID id-BAP-Header-Rewriting-Removed-List		CRITICALITY ignore	TYPE	BAP-Header-Rewriting-Removed-List	PRESENCE optional},
	...
}

BH-Routing-Information-Added-List ::= SEQUENCE (SIZE(1.. maxnoofRoutingEntries))	OF ProtocolIE-SingleContainer { { BH-Routing-Information-Added-List-ItemIEs } }
BH-Routing-Information-Removed-List ::= SEQUENCE (SIZE(1.. maxnoofRoutingEntries))	OF ProtocolIE-SingleContainer { { BH-Routing-Information-Removed-List-ItemIEs } }

BH-Routing-Information-Added-List-ItemIEs	F1AP-PROTOCOL-IES ::= {
	{ ID id-BH-Routing-Information-Added-List-Item				CRITICALITY ignore	TYPE BH-Routing-Information-Added-List-Item						PRESENCE mandatory},
	...
}

BH-Routing-Information-Removed-List-ItemIEs	F1AP-PROTOCOL-IES ::= {
	{ ID id-BH-Routing-Information-Removed-List-Item				CRITICALITY ignore	TYPE BH-Routing-Information-Removed-List-Item						PRESENCE mandatory},
	...
}

BAP-Header-Rewriting-Added-List ::= SEQUENCE (SIZE(1.. maxnoofRoutingEntries))	OF ProtocolIE-SingleContainer { { BAP-Header-Rewriting-Added-List-ItemIEs } }

BAP-Header-Rewriting-Added-List-ItemIEs F1AP-PROTOCOL-IES ::= {
	{ ID id-BAP-Header-Rewriting-Added-List-Item	CRITICALITY ignore	TYPE BAP-Header-Rewriting-Added-List-Item PRESENCE mandatory},
	...
}

BAP-Header-Rewriting-Removed-List ::= SEQUENCE (SIZE(1.. maxnoofRoutingEntries))	OF ProtocolIE-SingleContainer { { BAP-Header-Rewriting-Removed-List-ItemIEs } }

BAP-Header-Rewriting-Removed-List-ItemIEs F1AP-PROTOCOL-IES ::= {
	{ ID id-BAP-Header-Rewriting-Removed-List-Item	CRITICALITY ignore	TYPE BAP-Header-Rewriting-Removed-List-Item PRESENCE mandatory},
	...
}

-- **************************************************************
--
-- BAP MAPPING CONFIGURATION ACKNOWLEDGE
--
-- **************************************************************

BAPMappingConfigurationAcknowledge ::= SEQUENCE {
	protocolIEs		ProtocolIE-Container		{ {BAPMappingConfigurationAcknowledge-IEs} },
	...
}

BAPMappingConfigurationAcknowledge-IEs F1AP-PROTOCOL-IES ::= {
	{ ID id-TransactionID			CRITICALITY reject	TYPE	TransactionID			PRESENCE mandatory}|
	{ ID id-CriticalityDiagnostics	CRITICALITY ignore	TYPE	CriticalityDiagnostics	PRESENCE optional},
	...
}

-- **************************************************************
--
-- BAP MAPPING CONFIGURATION FAILURE
--
-- **************************************************************

BAPMappingConfigurationFailure ::= SEQUENCE {
	protocolIEs			ProtocolIE-Container		{ { BAPMappingConfigurationFailureIEs} },
	...
}

BAPMappingConfigurationFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}


-- **************************************************************
--
-- GNB-DU Configuration ELEMENTARY PROCEDURE
--
-- **************************************************************

-- **************************************************************
--
-- GNB-DU RESOURCE CONFIGURATION
--
-- **************************************************************


GNBDUResourceConfiguration ::= SEQUENCE {
	protocolIEs			ProtocolIE-Container		{{ GNBDUResourceConfigurationIEs}},
	...
}


GNBDUResourceConfigurationIEs F1AP-PROTOCOL-IES ::= {
	{ ID id-TransactionID							CRITICALITY reject	TYPE TransactionID								PRESENCE mandatory	}|
	{ ID id-Activated-Cells-to-be-Updated-List		CRITICALITY reject	TYPE Activated-Cells-to-be-Updated-List	PRESENCE optional}|
	{ ID id-Child-Nodes-List						CRITICALITY reject	TYPE Child-Nodes-List							PRESENCE optional}|
	{ ID id-Neighbour-Node-Cells-List				CRITICALITY reject	TYPE Neighbour-Node-Cells-List				PRESENCE optional}|
	{ ID id-Serving-Cells-List						CRITICALITY reject	TYPE Serving-Cells-List							PRESENCE optional},
	...
}




-- **************************************************************
--
-- GNB-DU RESOURCE CONFIGURATION ACKNOWLEDGE
--
-- **************************************************************


GNBDUResourceConfigurationAcknowledge ::= SEQUENCE {
	protocolIEs			ProtocolIE-Container		{ { GNBDUResourceConfigurationAcknowledgeIEs} },
	...
}


GNBDUResourceConfigurationAcknowledgeIEs F1AP-PROTOCOL-IES ::= {
	{ ID id-TransactionID						CRITICALITY reject	TYPE TransactionID							PRESENCE mandatory	}|
	{ ID id-CriticalityDiagnostics				CRITICALITY ignore	TYPE CriticalityDiagnostics					PRESENCE optional	},
	...
}

-- **************************************************************
--
-- GNB-DU RESOURCE CONFIGURATION FAILURE
--
-- **************************************************************

GNBDUResourceConfigurationFailure ::= SEQUENCE {
	protocolIEs			ProtocolIE-Container		{ { GNBDUResourceConfigurationFailureIEs} },
	...
}

GNBDUResourceConfigurationFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}


-- **************************************************************
--
-- IAB TNL Address Allocation ELEMENTARY PROCEDURE
--
-- **************************************************************

-- **************************************************************
--
-- IAB TNL ADDRESS REQUEST
--
-- **************************************************************



IABTNLAddressRequest ::= SEQUENCE {
	protocolIEs			ProtocolIE-Container		{ {IABTNLAddressRequestIEs} },
	...
}

IABTNLAddressRequestIEs F1AP-PROTOCOL-IES ::= {
	{ ID id-TransactionID						CRITICALITY reject	TYPE TransactionID								PRESENCE mandatory	}|
	{ ID id-IABv4AddressesRequested				CRITICALITY reject	TYPE IABv4AddressesRequested					PRESENCE optional	}|
	{ ID id-IABIPv6RequestType					CRITICALITY reject	TYPE IABIPv6RequestType							PRESENCE optional	}|
	{ ID id-IAB-TNL-Addresses-To-Remove-List	CRITICALITY reject	TYPE IAB-TNL-Addresses-To-Remove-List		PRESENCE optional	}|
	{ ID id-IAB-TNL-Addresses-Exception			CRITICALITY reject	TYPE IAB-TNL-Addresses-Exception				PRESENCE optional	},
	...
}


IAB-TNL-Addresses-To-Remove-List	::= SEQUENCE (SIZE(1..maxnoofTLAsIAB))	OF ProtocolIE-SingleContainer { { IAB-TNL-Addresses-To-Remove-ItemIEs } }

IAB-TNL-Addresses-To-Remove-ItemIEs	F1AP-PROTOCOL-IES::= {
	{ ID id-IAB-TNL-Addresses-To-Remove-Item			CRITICALITY reject	TYPE IAB-TNL-Addresses-To-Remove-Item					PRESENCE mandatory},
	...
}


-- **************************************************************
--
-- IAB TNL ADDRESS RESPONSE
--
-- **************************************************************


IABTNLAddressResponse ::= SEQUENCE {
	protocolIEs			ProtocolIE-Container		{ {IABTNLAddressResponseIEs} },
	...
}


IABTNLAddressResponseIEs F1AP-PROTOCOL-IES ::= {
	{ ID id-TransactionID								CRITICALITY reject	TYPE TransactionID									PRESENCE mandatory	}|
	{ ID id-IAB-Allocated-TNL-Address-List				CRITICALITY reject	TYPE IAB-Allocated-TNL-Address-List			PRESENCE mandatory	},
	...
}


IAB-Allocated-TNL-Address-List ::= SEQUENCE (SIZE(1.. maxnoofTLAsIAB))	OF ProtocolIE-SingleContainer { { IAB-Allocated-TNL-Address-List-ItemIEs } }


IAB-Allocated-TNL-Address-List-ItemIEs	F1AP-PROTOCOL-IES::= {
	{ ID id-IAB-Allocated-TNL-Address-Item			CRITICALITY reject	TYPE IAB-Allocated-TNL-Address-Item					PRESENCE mandatory},
	...
}

-- **************************************************************
--
-- IAB TNL ADDRESS FAILURE
--
-- **************************************************************

IABTNLAddressFailure ::= SEQUENCE {
	protocolIEs			ProtocolIE-Container		{ { IABTNLAddressFailureIEs} },
	...
}

IABTNLAddressFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}

-- **************************************************************
--
-- IAB UP Configuration Update ELEMENTARY PROCEDURE
--
-- **************************************************************

-- **************************************************************
--
-- IAB UP Configuration Update Request
--
-- **************************************************************

IABUPConfigurationUpdateRequest ::= SEQUENCE {
	protocolIEs			ProtocolIE-Container		{ { IABUPConfigurationUpdateRequestIEs} },
	...
}

IABUPConfigurationUpdateRequestIEs F1AP-PROTOCOL-IES ::= {
	{ ID id-TransactionID							CRITICALITY reject	TYPE TransactionID										PRESENCE mandatory  }|
	{ ID id-UL-UP-TNL-Information-to-Update-List	CRITICALITY ignore	TYPE UL-UP-TNL-Information-to-Update-List		PRESENCE optional	}|
	{ ID id-UL-UP-TNL-Address-to-Update-List		CRITICALITY ignore	TYPE UL-UP-TNL-Address-to-Update-List				PRESENCE optional	},
	...
}

UL-UP-TNL-Information-to-Update-List ::= SEQUENCE (SIZE(1.. maxnoofULUPTNLInformationforIAB))	OF ProtocolIE-SingleContainer { { UL-UP-TNL-Information-to-Update-List-ItemIEs } }

UL-UP-TNL-Information-to-Update-List-ItemIEs F1AP-PROTOCOL-IES ::= {
	{ ID id-UL-UP-TNL-Information-to-Update-List-Item	CRITICALITY ignore	TYPE UL-UP-TNL-Information-to-Update-List-Item PRESENCE mandatory },
	...
}

UL-UP-TNL-Address-to-Update-List ::= SEQUENCE (SIZE(1.. maxnoofUPTNLAddresses))	OF ProtocolIE-SingleContainer { { UL-UP-TNL-Address-to-Update-List-ItemIEs } }

UL-UP-TNL-Address-to-Update-List-ItemIEs F1AP-PROTOCOL-IES ::= {
	{ ID id-UL-UP-TNL-Address-to-Update-List-Item	CRITICALITY ignore	TYPE UL-UP-TNL-Address-to-Update-List-Item PRESENCE mandatory },
	...
}


-- **************************************************************
--
-- IAB UP Configuration Update Response
--
-- **************************************************************

IABUPConfigurationUpdateResponse ::= SEQUENCE {
	protocolIEs			ProtocolIE-Container		{ { IABUPConfigurationUpdateResponseIEs} },
	...
}

IABUPConfigurationUpdateResponseIEs F1AP-PROTOCOL-IES ::= {
	{ ID id-TransactionID						CRITICALITY reject	TYPE TransactionID							PRESENCE mandatory	}|
	{ ID id-CriticalityDiagnostics				CRITICALITY ignore	TYPE CriticalityDiagnostics					PRESENCE optional	}|
	{ ID id-DL-UP-TNL-Address-to-Update-List	CRITICALITY reject	TYPE DL-UP-TNL-Address-to-Update-List	PRESENCE optional	},
	...
}

DL-UP-TNL-Address-to-Update-List ::= SEQUENCE (SIZE(1.. maxnoofUPTNLAddresses))	OF ProtocolIE-SingleContainer { { DL-UP-TNL-Address-to-Update-List-ItemIEs } }

DL-UP-TNL-Address-to-Update-List-ItemIEs F1AP-PROTOCOL-IES ::= {
	{ ID id-DL-UP-TNL-Address-to-Update-List-Item	CRITICALITY ignore	TYPE DL-UP-TNL-Address-to-Update-List-Item	PRESENCE mandatory },
	...
}

-- **************************************************************
--
-- IAB UP Configuration Update Failure
--
-- **************************************************************

IABUPConfigurationUpdateFailure ::= SEQUENCE {
	protocolIEs			ProtocolIE-Container		{ { IABUPConfigurationUpdateFailureIEs} },
	...
}

IABUPConfigurationUpdateFailureIEs F1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}

-- MIAB F1 SETUP TRIGGERING PROCEDURE
--
-- **************************************************************


-- **************************************************************
--
-- MIAB F1 SETUP TRIGGERING
--
-- **************************************************************

MIABF1SetupTriggering ::= SEQUENCE {
	protocolIEs			ProtocolIE-Container       {{ MIABF1SetupTriggeringIEs}},
	...
}

MIABF1SetupTriggeringIEs F1AP-PROTOCOL-IES ::= {
	{ ID id-TransactionID						CRITICALITY reject	TYPE TransactionID							PRESENCE mandatory	}|
	{ ID id-Target-gNB-ID						CRITICALITY reject	TYPE GlobalGNB-ID							PRESENCE mandatory	}|
	{ ID id-Target-gNB-IP-address				CRITICALITY ignore	TYPE TransportLayerAddress					PRESENCE optional	}|
	{ ID id-Target-SeGW-IP-address				CRITICALITY ignore	TYPE TransportLayerAddress					PRESENCE optional	},
	...
}


-- MIAB F1 SETUP OUTCOME NOTIFICATION PROCEDURE
--
-- **************************************************************


-- **************************************************************
--
-- MIAB F1 SETUP OUTCOME NOTIFICATION
--
-- **************************************************************

MIABF1SetupOutcomeNotification ::= SEQUENCE {
	protocolIEs			ProtocolIE-Container       {{ MIABF1SetupOutcomeNotificationIEs}},
	...
}

MIABF1SetupOutcomeNotificationIEs F1AP-PROTOCOL-IES ::= {
	{ ID id-TransactionID						CRITICALITY reject	TYPE TransactionID								PRESENCE mandatory	}|
	{ ID id-F1SetupOutcome						CRITICALITY reject	TYPE F1SetupOutcome								PRESENCE mandatory	}|
	{ ID id-Activated-Cells-Mapping-List		CRITICALITY ignore	TYPE Activated-Cells-Mapping-List			PRESENCE optional	}|
	{ ID id-Target-F1-Terminating-Donor-gNB-ID	CRITICALITY reject	TYPE GlobalGNB-ID								PRESENCE optional	},
	...
}

F1SetupOutcome ::= ENUMERATED {success, failure,...}

Activated-Cells-Mapping-List ::= SEQUENCE (SIZE(1.. maxCellingNBDU))	OF ProtocolIE-SingleContainer { { Activated-Cells-Mapping-List-ItemIEs } }

Activated-Cells-Mapping-List-ItemIEs F1AP-PROTOCOL-IES ::= {
	{ ID id-Activated-Cells-Mapping-List-Item	CRITICALITY ignore	TYPE Activated-Cells-Mapping-List-Item PRESENCE mandatory },
	...
}



-- **************************************************************
--
-- Resource Status Reporting Initiation ELEMENTARY PROCEDURE
--
-- **************************************************************

-- **************************************************************
--
-- Resource Status Request
--
-- **************************************************************

ResourceStatusRequest::= SEQUENCE {
	protocolIEs			ProtocolIE-Container       { {ResourceStatusRequestIEs} },
	...
}

ResourceStatusRequestIEs F1AP-PROTOCOL-IES ::= {
	{ ID id-TransactionID			CRITICALITY reject	TYPE TransactionID			PRESENCE mandatory	}|
	{ ID id-gNBCUMeasurementID		CRITICALITY reject	TYPE GNBCUMeasurementID		PRESENCE mandatory	}|
	{ ID id-gNBDUMeasurementID		CRITICALITY ignore	TYPE GNBDUMeasurementID		PRESENCE conditional	}|
	-- The above IE shall be present if the Registration Request IE is set to the value "stop" or "add".
	{ ID id-RegistrationRequest		CRITICALITY ignore	TYPE RegistrationRequest	PRESENCE mandatory	}|
	{ ID id-ReportCharacteristics	CRITICALITY ignore	TYPE ReportCharacteristics	PRESENCE conditional	}|
	-- The above IE shall be present if the Registration Request IE is set to the value "start".
	{ ID id-CellToReportList		CRITICALITY ignore	TYPE CellToReportList		PRESENCE optional	}|
	{ ID id-ReportingPeriodicity	CRITICALITY ignore	TYPE ReportingPeriodicity	PRESENCE  optional	},
	...
}


-- **************************************************************
--
-- Resource Status Response
--
-- **************************************************************

ResourceStatusResponse ::= SEQUENCE {
	protocolIEs			ProtocolIE-Container       { { ResourceStatusResponseIEs} },
	...
}


ResourceStatusResponseIEs F1AP-PROTOCOL-IES ::= {
	{ ID id-TransactionID			CRITICALITY reject	TYPE TransactionID			PRESENCE mandatory	}|
	{ ID id-gNBCUMeasurementID		CRITICALITY reject	TYPE GNBCUMeasurementID		PRESENCE mandatory	}|
	{ ID id-gNBDUMeasurementID		CRITICALITY ignore	TYPE GNBDUMeasurementID		PRESENCE mandatory	}|
	{ ID id-CriticalityDiagnostics	CRITICALITY ignore	TYPE CriticalityDiagnostics	PRESENCE optional	},
	...
}


-- **************************************************************
--
-- Resource Status Failure
--
-- **************************************************************

ResourceStatusFailure ::= SEQUENCE {
	protocolIEs			ProtocolIE-Container       { { ResourceStatusFailureIEs} },
	...
}

ResourceStatusFailureIEs F1AP-PROTOCOL-IES ::= {
	{ ID id-TransactionID			CRITICALITY reject	TYPE TransactionID			PRESENCE mandatory	}|
	{ ID id-gNBCUMeasurementID		CRITICALITY reject	TYPE GNBCUMeasurementID		PRESENCE mandatory	}|
	{ ID id-gNBDUMeasurementID		CRITICALITY ignore	TYPE GNBDUMeasurementID		PRESENCE mandatory	}|
	{ ID id-Cause					CRITICALITY ignore	TYPE Cause					PRESENCE mandatory	}|
	{ ID id-CriticalityDiagnostics	CRITICALITY ignore	TYPE CriticalityDiagnostics	PRESENCE optional	},
	...
}

-- **************************************************************
--
-- Resource Status Reporting ELEMENTARY PROCEDURE
--
-- **************************************************************

-- **************************************************************
--
-- Resource Status Update
--
-- **************************************************************

ResourceStatusUpdate ::= SEQUENCE {
	protocolIEs			ProtocolIE-Container       {{ ResourceStatusUpdateIEs}},
	...
}

ResourceStatusUpdateIEs F1AP-PROTOCOL-IES ::= {
	{ ID id-TransactionID					CRITICALITY reject	TYPE TransactionID			PRESENCE mandatory	}|
	{ ID id-gNBCUMeasurementID			CRITICALITY reject	TYPE GNBCUMeasurementID				PRESENCE mandatory	}|
	{ ID id-gNBDUMeasurementID			CRITICALITY ignore	TYPE GNBDUMeasurementID			PRESENCE mandatory	}|
	{ ID id-HardwareLoadIndicator			CRITICALITY ignore	TYPE HardwareLoadIndicator			PRESENCE optional	}|
	{ ID id-TNLCapacityIndicator			CRITICALITY ignore	TYPE TNLCapacityIndicator		PRESENCE optional	}|
	{ ID id-CellMeasurementResultList		CRITICALITY ignore	TYPE CellMeasurementResultList	PRESENCE optional	}|
	{ ID id-NodeAssociatedInfoResult		CRITICALITY ignore	TYPE NodeAssociatedInfoResult	PRESENCE optional	},
	...
}

-- **************************************************************
--
--  Access And Mobility Indication ELEMENTARY PROCEDURE
--
-- **************************************************************

-- **************************************************************
--
-- Access And Mobility Indication
--
-- **************************************************************

AccessAndMobilityIndication ::= SEQUENCE {
	protocolIEs			ProtocolIE-Container       { { AccessAndMobilityIndicationIEs} },
	...
}

AccessAndMobilityIndicationIEs F1AP-PROTOCOL-IES ::= {
	{ ID id-TransactionID							CRITICALITY reject	TYPE TransactionID						PRESENCE mandatory }|
	{ ID id-RAReportList				CRITICALITY ignore	TYPE RAReportList			PRESENCE optional }|
	{ ID id-RLFReportInformationList				CRITICALITY ignore	TYPE RLFReportInformationList				PRESENCE optional }|
	{ ID id-SuccessfulHOReportInformationList		CRITICALITY ignore	TYPE SuccessfulHOReportInformationList	PRESENCE optional }|
	{ ID id-SuccessfulPSCellChangeReportInformationList	CRITICALITY ignore	TYPE SuccessfulPSCellChangeReportInformationList		PRESENCE optional }|
	{ ID id-FailureReportingWithoutRLFReport		CRITICALITY ignore 	TYPE FailureReportingWithoutRLFReport		PRESENCE optional }|
	{ ID id-MROForLTM-Information					CRITICALITY ignore 	TYPE MROForLTM-Information			PRESENCE optional },
	...
}


-- **************************************************************
--
-- REFERENCE TIME INFORMATION REPORTING CONTROL ELEMENTARY PROCEDURE
--
-- **************************************************************


-- **************************************************************
--
-- REFERENCE TIME INFORMATION REPORTING CONTROL
--
-- **************************************************************

ReferenceTimeInformationReportingControl::= SEQUENCE {
	protocolIEs		ProtocolIE-Container		{ { ReferenceTimeInformationReportingControlIEs} },
	...
}

ReferenceTimeInformationReportingControlIEs F1AP-PROTOCOL-IES ::= {
	{ ID id-TransactionID				CRITICALITY reject	TYPE TransactionID				PRESENCE mandatory	}|
	{ ID id-ReportingRequestType		CRITICALITY reject	TYPE ReportingRequestType		PRESENCE mandatory	},
	...
}


-- **************************************************************
--
-- REFERENCE TIME INFORMATION REPORT ELEMENTARY PROCEDURE
--
-- **************************************************************


-- **************************************************************
--
-- REFERENCE TIME INFORMATION REPORT
--
-- **************************************************************

ReferenceTimeInformationReport::= SEQUENCE {
	protocolIEs		ProtocolIE-Container		{ { ReferenceTimeInformationReportIEs} },
	...
}

ReferenceTimeInformationReportIEs F1AP-PROTOCOL-IES ::= {
	{ ID id-TransactionID				CRITICALITY ignore	TYPE TransactionID					PRESENCE mandatory	}|
	{ ID id-TimeReferenceInformation	CRITICALITY ignore	TYPE TimeReferenceInformation		PRESENCE mandatory	},
	...
}


-- **************************************************************
--
-- ACCESS SUCCESS ELEMENTARY PROCEDURE
--
-- **************************************************************

-- **************************************************************
--
-- Access Success
--
-- **************************************************************

AccessSuccess ::= SEQUENCE {
	protocolIEs			ProtocolIE-Container       {{ AccessSuccessIEs}},
	...
}

AccessSuccessIEs F1AP-PROTOCOL-IES ::= {
	{ ID id-gNB-CU-UE-F1AP-ID					CRITICALITY reject	TYPE GNB-CU-UE-F1AP-ID						PRESENCE mandatory	}|
	{ ID id-gNB-DU-UE-F1AP-ID					CRITICALITY reject	TYPE GNB-DU-UE-F1AP-ID						PRESENCE mandatory	}|
	{ ID id-NRCGI								CRITICALITY reject	TYPE NRCGI									PRESENCE mandatory	},
	...
}


-- **************************************************************
--
-- POSITIONING ASSISTANCE INFORMATION CONTROL ELEMENTARY PROCEDURE
--
-- **************************************************************

-- **************************************************************
--
-- Positioning Assistance Information Control
--
-- **************************************************************

PositioningAssistanceInformationControl ::= SEQUENCE {
	protocolIEs			ProtocolIE-Container       {{ PositioningAssistanceInformationControlIEs}},
	...
}

PositioningAssistanceInformationControlIEs F1AP-PROTOCOL-IES ::= {
		{ ID id-TransactionID					CRITICALITY reject	TYPE TransactionID				PRESENCE mandatory	}|
		{ ID id-PosAssistance-Information		CRITICALITY reject	TYPE PosAssistance-Information		PRESENCE optional}|
		{ ID id-PosBroadcast					CRITICALITY reject	TYPE PosBroadcast				PRESENCE optional}|
		{ ID id-PositioningBroadcastCells		CRITICALITY reject	TYPE PositioningBroadcastCells		PRESENCE optional}|
		{ ID id-RoutingID						CRITICALITY reject	TYPE RoutingID				PRESENCE optional},
	...
}

-- **************************************************************
--
-- POSITIONING ASSISTANCE INFORMATION FEEDBACK ELEMENTARY PROCEDURE
--
-- **************************************************************

-- **************************************************************
--
-- Positioning Assistance Information Feedback
--
-- **************************************************************

PositioningAssistanceInformationFeedback ::= SEQUENCE {
	protocolIEs			ProtocolIE-Container       {{ PositioningAssistanceInformationFeedbackIEs}},
	...
}

PositioningAssistanceInformationFeedbackIEs F1AP-PROTOCOL-IES ::= {
	{ ID id-TransactionID							CRITICALITY reject	TYPE TransactionID							PRESENCE mandatory	}|
	{ ID id-PosAssistanceInformationFailureList	CRITICALITY reject	TYPE PosAssistanceInformationFailureList	PRESENCE optional}|
	{ ID id-PositioningBroadcastCells				CRITICALITY reject	TYPE PositioningBroadcastCells				PRESENCE optional}|
	{ ID id-RoutingID								CRITICALITY reject	TYPE RoutingID									PRESENCE optional}|
	{ ID id-CriticalityDiagnostics				CRITICALITY ignore	TYPE CriticalityDiagnostics						PRESENCE optional},
	...
}

-- **************************************************************
--
-- POSITONING MEASUREMENT EXCHANGE ELEMENTARY PROCEDURE
--
-- **************************************************************

-- **************************************************************
--
-- Positioning Measurement Request
--
-- **************************************************************

PositioningMeasurementRequest ::= SEQUENCE {
	protocolIEs			ProtocolIE-Container       { { PositioningMeasurementRequestIEs} },
	...
}

PositioningMeasurementRequestIEs F1AP-PROTOCOL-IES ::= {
	{ ID id-TransactionID							CRITICALITY reject	TYPE TransactionID									PRESENCE mandatory}|
	{ ID id-LMF-MeasurementID						CRITICALITY reject	TYPE LMF-MeasurementID								PRESENCE mandatory}|
	{ ID id-RAN-MeasurementID						CRITICALITY reject	TYPE RAN-MeasurementID								PRESENCE mandatory}|
	{ ID id-TRP-MeasurementRequestList				CRITICALITY reject	TYPE TRP-MeasurementRequestList					PRESENCE mandatory}|
	{ ID id-PosReportCharacteristics				CRITICALITY reject	TYPE PosReportCharacteristics					PRESENCE mandatory}|
	{ ID id-PosMeasurementPeriodicity				CRITICALITY reject	TYPE MeasurementPeriodicity						PRESENCE conditional }|
	-- The above IE shall be present if the PosReportCharacteristics IE is set to "periodic" --
	{ ID id-PosMeasurementQuantities				CRITICALITY reject	TYPE PosMeasurementQuantities					PRESENCE mandatory}|
	{ ID id-SFNInitialisationTime					CRITICALITY ignore	TYPE RelativeTime1900	PRESENCE optional	}|
	{ ID id-SRSConfiguration						CRITICALITY ignore	TYPE SRSConfiguration								PRESENCE optional}|
	{ ID id-MeasurementBeamInfoRequest				CRITICALITY ignore	TYPE MeasurementBeamInfoRequest	PRESENCE optional	}|
	{ ID id-SystemFrameNumber						CRITICALITY ignore	TYPE SystemFrameNumber		PRESENCE optional}|
	{ ID id-SlotNumber								CRITICALITY ignore	TYPE SlotNumber				PRESENCE optional}|
	{ ID id-PosMeasurementPeriodicityExtended		CRITICALITY reject	TYPE MeasurementPeriodicityExtended			PRESENCE conditional }|
	-- The IE shall be present the MeasurementPeriodicity IE is set to the value "extended"

	{ ID id-ResponseTime							CRITICALITY ignore	TYPE ResponseTime									PRESENCE optional}|
	{ ID id-MeasurementCharacteristicsRequestIndicator			CRITICALITY ignore	TYPE MeasurementCharacteristicsRequestIndicator	PRESENCE optional}|
	{ ID id-MeasurementTimeOccasion					CRITICALITY ignore	TYPE MeasurementTimeOccasion	PRESENCE optional	}|
	{ ID id-PosMeasurementAmount					CRITICALITY ignore	TYPE PosMeasurementAmount	PRESENCE optional	}|
	{ ID id-TimeWindowInformation-Measurement-List		CRITICALITY ignore	TYPE TimeWindowInformation-Measurement-List	PRESENCE optional	},
	...
}


-- **************************************************************
--
-- Positioning Measurement Response
--
-- **************************************************************

PositioningMeasurementResponse ::= SEQUENCE {
	protocolIEs			ProtocolIE-Container       { { PositioningMeasurementResponseIEs} },
	...
}


PositioningMeasurementResponseIEs F1AP-PROTOCOL-IES ::= {
	{ ID id-TransactionID							CRITICALITY reject	TYPE TransactionID									PRESENCE mandatory}|
	{ ID id-LMF-MeasurementID						CRITICALITY reject	TYPE LMF-MeasurementID								PRESENCE mandatory}|
	{ ID id-RAN-MeasurementID						CRITICALITY reject	TYPE RAN-MeasurementID								PRESENCE mandatory}|
	{ ID id-PosMeasurementResultList				CRITICALITY reject	TYPE PosMeasurementResultList					PRESENCE optional	}|
	{ ID id-CriticalityDiagnostics					CRITICALITY ignore	TYPE CriticalityDiagnostics						PRESENCE optional	},
	...
}


-- **************************************************************
--
-- Positioning Measurement Failure
--
-- **************************************************************

PositioningMeasurementFailure ::= SEQUENCE {
	protocolIEs			ProtocolIE-Container       { { PositioningMeasurementFailureIEs} },
	...
}

PositioningMeasurementFailureIEs F1AP-PROTOCOL-IES ::= {
	{ ID id-TransactionID					CRITICALITY reject	TYPE TransactionID				PRESENCE mandatory	}|
	{ ID id-LMF-MeasurementID				CRITICALITY reject	TYPE LMF-MeasurementID			PRESENCE mandatory	}|
	{ ID id-RAN-MeasurementID				CRITICALITY reject	TYPE RAN-MeasurementID				PRESENCE mandatory	}|
	{ ID id-Cause							CRITICALITY ignore	TYPE Cause							PRESENCE mandatory	}|
	{ ID id-CriticalityDiagnostics			CRITICALITY ignore	TYPE CriticalityDiagnostics			PRESENCE optional	},
	...
}


-- **************************************************************
--
-- POSITIONING MEASUREMENT REPORT ELEMENTARY PROCEDURE
--
-- **************************************************************

-- **************************************************************
--
-- Positioning Measurement Report
--
-- **************************************************************

PositioningMeasurementReport ::= SEQUENCE {
	protocolIEs		ProtocolIE-Container		{ { PositioningMeasurementReportIEs} },
	...
}

PositioningMeasurementReportIEs F1AP-PROTOCOL-IES ::= {
	{ ID id-TransactionID				CRITICALITY reject	TYPE TransactionID				PRESENCE mandatory	}|
	{ ID id-LMF-MeasurementID			CRITICALITY reject	TYPE LMF-MeasurementID			PRESENCE mandatory	}|
	{ ID id-RAN-MeasurementID			CRITICALITY reject	TYPE RAN-MeasurementID			PRESENCE mandatory	}|
	{ ID id-PosMeasurementResultList	CRITICALITY reject	TYPE PosMeasurementResultList	PRESENCE mandatory	},
	...
}

-- **************************************************************
--
-- POSITIONING MEASUREMENT ABORT ELEMENTARY PROCEDURE
--
-- **************************************************************

-- **************************************************************
--
-- Positioning Measurement Abort
--
-- **************************************************************

PositioningMeasurementAbort ::= SEQUENCE {
	protocolIEs		ProtocolIE-Container		{ { PositioningMeasurementAbortIEs} },
	...
}

PositioningMeasurementAbortIEs F1AP-PROTOCOL-IES ::= {
	{ ID id-TransactionID					CRITICALITY reject	TYPE TransactionID					PRESENCE mandatory	}|
	{ ID id-LMF-MeasurementID				CRITICALITY reject	TYPE LMF-MeasurementID				PRESENCE mandatory	}|
	{ ID id-RAN-MeasurementID				CRITICALITY reject	TYPE RAN-MeasurementID				PRESENCE mandatory	},
	...
}

-- **************************************************************
--
-- POSITIONING MEASUREMENT FAILURE INDICATION ELEMENTARY PROCEDURE
--
-- **************************************************************

-- **************************************************************
--
-- Positioning Measurement Failure Indication
--
-- **************************************************************

PositioningMeasurementFailureIndication ::= SEQUENCE {
	protocolIEs		ProtocolIE-Container		{ { PositioningMeasurementFailureIndicationIEs} },
	...
}

PositioningMeasurementFailureIndicationIEs F1AP-PROTOCOL-IES ::= {
	{ ID id-TransactionID				CRITICALITY reject	TYPE TransactionID					PRESENCE mandatory	}|
	{ ID id-LMF-MeasurementID			CRITICALITY reject	TYPE LMF-MeasurementID				PRESENCE mandatory	}|
	{ ID id-RAN-MeasurementID			CRITICALITY reject	TYPE RAN-MeasurementID				PRESENCE mandatory	}|
	{ ID id-Cause						CRITICALITY ignore	TYPE Cause							PRESENCE mandatory	},
	...
}

-- **************************************************************
--
-- POSITIONING MEASUREMENT UPDATE ELEMENTARY PROCEDURE
--
-- **************************************************************

-- **************************************************************
--
-- Positioning Measurement Update
--
-- **************************************************************

PositioningMeasurementUpdate ::= SEQUENCE {
	protocolIEs		ProtocolIE-Container		{ { PositioningMeasurementUpdateIEs} },
	...
}

PositioningMeasurementUpdateIEs F1AP-PROTOCOL-IES ::= {
	{ ID id-TransactionID				CRITICALITY reject	TYPE TransactionID				PRESENCE mandatory	}|
	{ ID id-LMF-MeasurementID			CRITICALITY reject	TYPE LMF-MeasurementID			PRESENCE mandatory	}|
	{ ID id-RAN-MeasurementID			CRITICALITY reject	TYPE RAN-MeasurementID			PRESENCE mandatory	}|
	{ ID id-SRSConfiguration			CRITICALITY ignore	TYPE SRSConfiguration			PRESENCE optional}|
	{ ID id-TRP-MeasurementUpdateList	CRITICALITY reject	TYPE TRP-MeasurementUpdateList 	PRESENCE optional}|
	{ ID id-MeasurementCharacteristicsRequestIndicator	CRITICALITY ignore	TYPE	MeasurementCharacteristicsRequestIndicator	PRESENCE optional}|
	{ ID id-MeasurementTimeOccasion		CRITICALITY ignore	TYPE MeasurementTimeOccasion	PRESENCE optional	},
	...
}


-- **************************************************************
--
-- TRP INFORMATION EXCHANGE ELEMENTARY PROCEDURE
--
-- **************************************************************

-- **************************************************************
--
-- TRP Information Request
--
-- **************************************************************

TRPInformationRequest ::= SEQUENCE {
	protocolIEs		ProtocolIE-Container		{ { TRPInformationRequestIEs} },
	...
}

TRPInformationRequestIEs F1AP-PROTOCOL-IES ::= {
	{ ID id-TransactionID						CRITICALITY reject	TYPE TransactionID								PRESENCE mandatory	}|
	{ ID id-TRPList								CRITICALITY ignore	TYPE TRPList									PRESENCE optional	}|
	{ ID id-TRPInformationTypeListTRPReq		CRITICALITY reject	TYPE TRPInformationTypeListTRPReq			PRESENCE mandatory	},
	...
}

TRPInformationTypeListTRPReq ::= SEQUENCE (SIZE(1.. maxnoofTRPInfoTypes)) OF ProtocolIE-SingleContainer { { TRPInformationTypeItemTRPReq } }

TRPInformationTypeItemTRPReq 	F1AP-PROTOCOL-IES ::= {
	{ ID id-TRPInformationTypeItem	 CRITICALITY reject		TYPE TRPInformationTypeItem  	PRESENCE mandatory },
	...
}


-- **************************************************************
--
-- TRP Information Response
--
-- **************************************************************

TRPInformationResponse ::= SEQUENCE {
	protocolIEs		ProtocolIE-Container		{ { TRPInformationResponseIEs} },
	...
}

TRPInformationResponseIEs F1AP-PROTOCOL-IES ::= {
	{ ID id-TransactionID					CRITICALITY reject	TYPE TransactionID					PRESENCE mandatory	}|
	{ ID id-TRPInformationListTRPResp		CRITICALITY ignore	TYPE TRPInformationListTRPResp		PRESENCE mandatory	}|
	{ ID id-CriticalityDiagnostics			CRITICALITY ignore	TYPE CriticalityDiagnostics			PRESENCE optional	},
	...
}

TRPInformationListTRPResp ::= SEQUENCE (SIZE(1.. maxnoofTRPs)) OF ProtocolIE-SingleContainer { { TRPInformationItemTRPResp } }

TRPInformationItemTRPResp 	F1AP-PROTOCOL-IES ::= {
	{ ID id-TRPInformationItem	 CRITICALITY ignore		TYPE TRPInformationItem  	PRESENCE mandatory },
	...
}


-- **************************************************************
--
-- TRP Information Failure
--
-- **************************************************************

TRPInformationFailure ::= SEQUENCE {
	protocolIEs		ProtocolIE-Container		{ { TRPInformationFailureIEs} },
	...
}

TRPInformationFailureIEs F1AP-PROTOCOL-IES ::= {
	{ ID id-TransactionID				CRITICALITY reject	TYPE TransactionID				PRESENCE mandatory	}|
	{ ID id-Cause						CRITICALITY ignore	TYPE Cause						PRESENCE mandatory	}|
	{ ID id-CriticalityDiagnostics		CRITICALITY ignore	TYPE CriticalityDiagnostics		PRESENCE optional	},
	...
}


-- **************************************************************
--
-- POSITIONING INFORMATION EXCHANGE ELEMENTARY PROCEDURE
--
-- **************************************************************

-- **************************************************************
--
-- Positioning Information Request
--
-- **************************************************************

PositioningInformationRequest ::= SEQUENCE {
	protocolIEs			ProtocolIE-Container       { { PositioningInformationRequestIEs} },
	...
}

PositioningInformationRequestIEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY reject	TYPE GNB-DU-UE-F1AP-ID									PRESENCE mandatory	}|
	{ ID id-RequestedSRSTransmissionCharacteristics	CRITICALITY ignore	TYPE RequestedSRSTransmissionCharacteristics	PRESENCE optional}|
	{ ID id-UEReportingInformation					CRITICALITY ignore	TYPE UEReportingInformation							PRESENCE optional}|
	{ ID id-SRSPosRRCInactiveQueryIndication		CRITICALITY ignore	TYPE SRSPosRRCInactiveQueryIndication				PRESENCE optional}|
	{ ID id-TimeWindowInformation-SRS-List			CRITICALITY ignore	TYPE TimeWindowInformation-SRS-List						PRESENCE optional}|
	{ ID id-RequestedSRSPreconfigurationCharacteristics-List	CRITICALITY ignore	TYPE RequestedSRSPreconfigurationCharacteristics-List 	PRESENCE optional	},
	...
}


-- **************************************************************
--
-- Positioning Information Response
--
-- **************************************************************

PositioningInformationResponse ::= SEQUENCE {
	protocolIEs			ProtocolIE-Container       { { PositioningInformationResponseIEs} },
	...
}


PositioningInformationResponseIEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-SRSConfiguration			CRITICALITY ignore	TYPE SRSConfiguration			PRESENCE optional}|
	{ ID id-SFNInitialisationTime		CRITICALITY ignore	TYPE RelativeTime1900			PRESENCE optional}|
	{ ID id-CriticalityDiagnostics		CRITICALITY ignore	TYPE CriticalityDiagnostics		PRESENCE optional }|
	{ ID id-SRSPosRRCInactiveConfig		CRITICALITY ignore	TYPE SRSPosRRCInactiveConfig	PRESENCE optional}|
	{ ID id-SRSPosRRCInactiveValidityAreaConfig		CRITICALITY ignore	TYPE SRSPosRRCInactiveValidityAreaConfig	PRESENCE optional}|
	{ ID id-SRSPreconfiguration-List	CRITICALITY ignore	TYPE SRSPreconfiguration-List	PRESENCE optional},
	...
}


-- **************************************************************
--
-- Positioning Information Failure
--
-- **************************************************************

PositioningInformationFailure ::= SEQUENCE {
	protocolIEs			ProtocolIE-Container       { { PositioningInformationFailureIEs} },
	...
}

PositioningInformationFailureIEs F1AP-PROTOCOL-IES ::= {

	{ ID id-gNB-CU-UE-F1AP-ID		CRITICALITY reject	TYPE GNB-CU-UE-F1AP-ID			PRESENCE mandatory	}|
	{ ID id-gNB-DU-UE-F1AP-ID		CRITICALITY reject	TYPE GNB-DU-UE-F1AP-ID			PRESENCE mandatory	}|
	{ ID id-Cause						CRITICALITY ignore	TYPE Cause						PRESENCE mandatory	}|
	{ ID id-CriticalityDiagnostics		CRITICALITY ignore	TYPE CriticalityDiagnostics		PRESENCE optional },
	...
}


-- **************************************************************
--
-- POSITIONING ACTIVATION ELEMENTARY PROCEDURE
--
-- **************************************************************

-- **************************************************************
--
-- Positioning Activation Request
--
-- **************************************************************

PositioningActivationRequest ::= SEQUENCE {
	protocolIEs			ProtocolIE-Container       { { PositioningActivationRequestIEs} },
	...
}

PositioningActivationRequestIEs F1AP-PROTOCOL-IES ::= {
	{ ID id-gNB-CU-UE-F1AP-ID		CRITICALITY reject	TYPE GNB-CU-UE-F1AP-ID			PRESENCE mandatory	}|
	{ ID id-gNB-DU-UE-F1AP-ID		CRITICALITY reject	TYPE GNB-DU-UE-F1AP-ID			PRESENCE mandatory	}|
	{ ID id-SRSType					CRITICALITY reject	TYPE SRSType					PRESENCE mandatory	}|
	{ ID id-ActivationTime			CRITICALITY ignore	TYPE RelativeTime1900		PRESENCE optional	},
	...
}

SRSType ::= CHOICE {
	semipersistentSRS				SemipersistentSRS,
	aperiodicSRS					AperiodicSRS,
	choice-extension				ProtocolIE-SingleContainer { { SRSType-ExtIEs} }
}

SRSType-ExtIEs F1AP-PROTOCOL-IES ::= {
	...
}

SemipersistentSRS ::= SEQUENCE {
	sRSResourceSetID			SRSResourceSetID,
	sRSSpatialRelation			SpatialRelationInfo	OPTIONAL,
	iE-Extensions				ProtocolExtensionContainer { {SemipersistentSRS-ExtIEs} } OPTIONAL,
	...
}

SemipersistentSRS-ExtIEs F1AP-PROTOCOL-EXTENSION ::= {
	{ ID id-SRSSpatialRelationPerSRSResource	CRITICALITY ignore	EXTENSION SpatialRelationPerSRSResource PRESENCE optional}|
	{ ID id-AggregatedPosSRSResourceSetList	CRITICALITY ignore EXTENSION AggregatedPosSRSResourceSetList	PRESENCE optional},
	...
}

AperiodicSRS ::= SEQUENCE {
	aperiodic					ENUMERATED {true, ...},
	sRSResourceTrigger			SRSResourceTrigger		OPTIONAL,
	iE-Extensions				ProtocolExtensionContainer { {AperiodicSRS-ExtIEs} } OPTIONAL,
	...
}

AperiodicSRS-ExtIEs F1AP-PROTOCOL-EXTENSION ::= {
	{ ID id-AggregatedPosSRSResourceSetList	CRITICALITY ignore EXTENSION AggregatedPosSRSResourceSetList	PRESENCE optional},
	...
}


-- **************************************************************
--
-- Positioning Activation Response
--
-- **************************************************************

PositioningActivationResponse ::= SEQUENCE {
	protocolIEs			ProtocolIE-Container       { { PositioningActivationResponseIEs} },
	...
}


PositioningActivationResponseIEs F1AP-PROTOCOL-IES ::= {
	{ ID id-gNB-CU-UE-F1AP-ID		CRITICALITY reject	TYPE GNB-CU-UE-F1AP-ID			PRESENCE mandatory	}|
	{ ID id-gNB-DU-UE-F1AP-ID		CRITICALITY reject	TYPE GNB-DU-UE-F1AP-ID			PRESENCE mandatory	}|
	{ ID id-SystemFrameNumber		CRITICALITY ignore	TYPE SystemFrameNumber			PRESENCE optional }|
	{ ID id-SlotNumber				CRITICALITY ignore	TYPE SlotNumber					PRESENCE optional }|
	{ ID id-CriticalityDiagnostics	CRITICALITY ignore	TYPE CriticalityDiagnostics		PRESENCE optional },
	...
}




-- **************************************************************
--
-- Positioning Activation Failure
--
-- **************************************************************

PositioningActivationFailure ::= SEQUENCE {
	protocolIEs			ProtocolIE-Container       { { PositioningActivationFailureIEs} },
	...
}

PositioningActivationFailureIEs F1AP-PROTOCOL-IES ::= {
	{ ID id-gNB-CU-UE-F1AP-ID		CRITICALITY reject	TYPE GNB-CU-UE-F1AP-ID				PRESENCE mandatory	}|
	{ ID id-gNB-DU-UE-F1AP-ID		CRITICALITY reject	TYPE GNB-DU-UE-F1AP-ID				PRESENCE mandatory	}|
	{ ID id-Cause						CRITICALITY ignore	TYPE Cause						PRESENCE mandatory	}|
	{ ID id-CriticalityDiagnostics		CRITICALITY ignore	TYPE CriticalityDiagnostics		PRESENCE optional },
	...
}


-- **************************************************************
--
-- POSITIONING DEACTIVATION ELEMENTARY PROCEDURE
--
-- **************************************************************

-- **************************************************************
--
-- Positioning Deactivation
--
-- **************************************************************

PositioningDeactivation ::= SEQUENCE {
	protocolIEs			ProtocolIE-Container       { { PositioningDeactivationIEs} },
	...
}

PositioningDeactivationIEs F1AP-PROTOCOL-IES ::= {
	{ ID id-gNB-CU-UE-F1AP-ID		CRITICALITY reject	TYPE GNB-CU-UE-F1AP-ID			PRESENCE mandatory	}|
	{ ID id-gNB-DU-UE-F1AP-ID		CRITICALITY reject	TYPE GNB-DU-UE-F1AP-ID			PRESENCE mandatory	}|
	{ ID id-AbortTransmission		CRITICALITY ignore	TYPE AbortTransmission			PRESENCE mandatory	},
	...
}

-- **************************************************************
--
-- POSITIONING INFORMATION UPDATE ELEMENTARY PROCEDURE
--
-- **************************************************************

-- **************************************************************
--
-- Positioning Information Update
--
-- **************************************************************

PositioningInformationUpdate ::= SEQUENCE {
	protocolIEs			ProtocolIE-Container       { { PositioningInformationUpdateIEs} },
	...
}


PositioningInformationUpdateIEs F1AP-PROTOCOL-IES ::= {
	{ ID id-gNB-CU-UE-F1AP-ID		CRITICALITY reject	TYPE GNB-CU-UE-F1AP-ID			PRESENCE mandatory	}|
	{ ID id-gNB-DU-UE-F1AP-ID		CRITICALITY reject	TYPE GNB-DU-UE-F1AP-ID			PRESENCE mandatory	}|
	{ ID id-SRSConfiguration		CRITICALITY ignore	TYPE SRSConfiguration			PRESENCE optional}|
	{ ID id-SFNInitialisationTime	CRITICALITY ignore	TYPE RelativeTime1900			PRESENCE optional},
	...
}

-- **************************************************************
--
-- SRS Information Reservation Notification
--
-- **************************************************************

SRSInformationReservationNotification ::= SEQUENCE {
	protocolIEs			ProtocolIE-Container       {{ SRSInformationReservationNotificationIEs}},
	...
}

SRSInformationReservationNotificationIEs F1AP-PROTOCOL-IES ::= {
	{ ID id-TransactionID			CRITICALITY reject	TYPE TransactionID					PRESENCE mandatory	}|
	{ ID id-SRSReservationType		CRITICALITY reject	TYPE SRSReservationType			PRESENCE mandatory	}|
	{ ID id-SRSInformation			CRITICALITY ignore	TYPE RequestedSRSTransmissionCharacteristics				PRESENCE optional	}|
	{ ID id-PreconfiguredSRSInformation	CRITICALITY ignore	TYPE RequestedSRSPreconfigurationCharacteristics-List				PRESENCE optional },
	...
}


-- **************************************************************
--
-- E-CID MEASUREMENT ELEMENTARY PROCEDURE
--
-- **************************************************************

-- **************************************************************
--
-- E-CID Measurement Initiation Request
--
-- **************************************************************

E-CIDMeasurementInitiationRequest ::= SEQUENCE {
	protocolIEs		ProtocolIE-Container	{{E-CIDMeasurementInitiationRequest-IEs}},
	...
}

E-CIDMeasurementInitiationRequest-IEs F1AP-PROTOCOL-IES ::= {
	{ ID id-gNB-CU-UE-F1AP-ID				CRITICALITY reject	TYPE GNB-CU-UE-F1AP-ID					PRESENCE mandatory	}|
	{ ID id-gNB-DU-UE-F1AP-ID				CRITICALITY reject	TYPE GNB-DU-UE-F1AP-ID					PRESENCE mandatory	}|
	{ ID id-LMF-UE-MeasurementID			CRITICALITY reject	TYPE LMF-UE-MeasurementID				PRESENCE mandatory	}|
	{ ID id-RAN-UE-MeasurementID			CRITICALITY reject	TYPE RAN-UE-MeasurementID				PRESENCE mandatory	}|
	{ ID id-E-CID-ReportCharacteristics		CRITICALITY reject	TYPE E-CID-ReportCharacteristics		PRESENCE mandatory	}|
	{ ID id-E-CID-MeasurementPeriodicity	CRITICALITY reject	TYPE MeasurementPeriodicity		PRESENCE conditional	}|
	-- The above IE shall be present if the E-CID-ReportCharacteristics IE is set to "periodic" --
	{ ID id-E-CID-MeasurementQuantities		CRITICALITY reject	TYPE E-CID-MeasurementQuantities	PRESENCE mandatory}|
	{ ID id-PosMeasurementPeriodicityNR-AoA	CRITICALITY reject	TYPE PosMeasurementPeriodicityNR-AoA		PRESENCE conditional},
	-- The IE shall be present if the E-CID-ReportCharacteristics IE is set to "periodic" and the E-CID-MeasurementQuantities-Item IE in the E-CID-MeasurementQuantities IE is set to the value "angleOfArrivalNR"--
	...
}

-- **************************************************************
--
-- E-CID Measurement Initiation Response
--
-- **************************************************************

E-CIDMeasurementInitiationResponse ::= SEQUENCE {
	protocolIEs		ProtocolIE-Container	{{E-CIDMeasurementInitiationResponse-IEs}},
	...
}

E-CIDMeasurementInitiationResponse-IEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-LMF-UE-MeasurementID		CRITICALITY reject	TYPE LMF-UE-MeasurementID			PRESENCE mandatory	}|
	{ ID id-RAN-UE-MeasurementID		CRITICALITY reject	TYPE RAN-UE-MeasurementID			PRESENCE mandatory	}|
	{ ID id-E-CID-MeasurementResult		CRITICALITY ignore	TYPE E-CID-MeasurementResult		PRESENCE optional}|
	{ ID id-Cell-Portion-ID				CRITICALITY ignore	TYPE Cell-Portion-ID				PRESENCE optional}|
	{ ID id-CriticalityDiagnostics		CRITICALITY ignore	TYPE CriticalityDiagnostics			PRESENCE optional},
	...
}

-- **************************************************************
--
-- E-CID Measurement Initiation Failure
--
-- **************************************************************

E-CIDMeasurementInitiationFailure ::= SEQUENCE {
	protocolIEs						ProtocolIE-Container		{{E-CIDMeasurementInitiationFailure-IEs}},
	...
}


E-CIDMeasurementInitiationFailure-IEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-LMF-UE-MeasurementID		CRITICALITY reject	TYPE LMF-UE-MeasurementID			PRESENCE mandatory	}|
	{ ID id-RAN-UE-MeasurementID		CRITICALITY reject	TYPE RAN-UE-MeasurementID			PRESENCE mandatory	}|
	{ ID id-Cause						CRITICALITY ignore	TYPE Cause							PRESENCE mandatory	}|
	{ ID id-CriticalityDiagnostics		CRITICALITY ignore	TYPE CriticalityDiagnostics			PRESENCE optional},
	...
}

-- **************************************************************
--
-- E-CID MEASUREMENT FAILURE INDICATION ELEMENTARY PROCEDURE
--
-- **************************************************************

-- **************************************************************
--
-- E-CID Measurement Failure Indication
--
-- **************************************************************

E-CIDMeasurementFailureIndication ::= SEQUENCE {
	protocolIEs						ProtocolIE-Container		{{E-CIDMeasurementFailureIndication-IEs}},
	...
}


E-CIDMeasurementFailureIndication-IEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-LMF-UE-MeasurementID		CRITICALITY reject	TYPE LMF-UE-MeasurementID		PRESENCE mandatory	}|
	{ ID id-RAN-UE-MeasurementID		CRITICALITY reject	TYPE RAN-UE-MeasurementID		PRESENCE mandatory	}|
	{ ID id-Cause						CRITICALITY ignore	TYPE Cause						PRESENCE mandatory},
	...
}

-- **************************************************************
--
-- E-CID MEASUREMENT REPORT ELEMENTARY PROCEDURE
--
-- **************************************************************

-- **************************************************************
--
-- E-CID Measurement Report
--
-- **************************************************************

E-CIDMeasurementReport ::= SEQUENCE {
	protocolIEs						ProtocolIE-Container		{{E-CIDMeasurementReport-IEs}},
	...
}


E-CIDMeasurementReport-IEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-LMF-UE-MeasurementID		CRITICALITY reject	TYPE LMF-UE-MeasurementID			PRESENCE mandatory	}|
	{ ID id-RAN-UE-MeasurementID		CRITICALITY reject	TYPE RAN-UE-MeasurementID			PRESENCE mandatory	}|
	{ ID id-E-CID-MeasurementResult		CRITICALITY ignore	TYPE E-CID-MeasurementResult		PRESENCE mandatory }|
	{ ID id-Cell-Portion-ID				CRITICALITY ignore	TYPE Cell-Portion-ID				PRESENCE optional},

	...
}

-- **************************************************************
--
-- E-CID MEASUREMENT TERMINATION ELEMENTARY PROCEDURE
--
-- **************************************************************

-- **************************************************************
--
-- E-CID Measurement Termination Command
--
-- **************************************************************


E-CIDMeasurementTerminationCommand ::= SEQUENCE {
	protocolIEs						ProtocolIE-Container		{{E-CIDMeasurementTerminationCommand-IEs}},
	...
}


E-CIDMeasurementTerminationCommand-IEs F1AP-PROTOCOL-IES ::= {
	{ ID id-gNB-CU-UE-F1AP-ID			CRITICALITY reject	TYPE GNB-CU-UE-F1AP-ID					PRESENCE mandatory	}|
	{ ID id-gNB-DU-UE-F1AP-ID			CRITICALITY reject	TYPE GNB-DU-UE-F1AP-ID					PRESENCE mandatory	}|
	{ ID id-LMF-UE-MeasurementID		CRITICALITY reject	TYPE LMF-UE-MeasurementID				PRESENCE mandatory	}|
	{ ID id-RAN-UE-MeasurementID		CRITICALITY reject	TYPE RAN-UE-MeasurementID				PRESENCE mandatory	},
	...
}

-- **************************************************************
--
-- BROADCAST CONTEXT SETUP ELEMENTARY PROCEDURE
--
-- **************************************************************

-- **************************************************************
--
-- BROADCAST CONTEXT SETUP REQUEST
--
-- **************************************************************

BroadcastContextSetupRequest ::= SEQUENCE {
	protocolIEs			ProtocolIE-Container       { { BroadcastContextSetupRequestIEs} },
	...
}

BroadcastContextSetupRequestIEs F1AP-PROTOCOL-IES ::= {
	{ ID id-gNB-CU-MBS-F1AP-ID					CRITICALITY reject	TYPE	GNB-CU-MBS-F1AP-ID						PRESENCE mandatory	}|
	{ ID id-MBS-Session-ID						CRITICALITY reject 	TYPE	MBS-Session-ID							PRESENCE mandatory	}|
	{ ID id-MBS-ServiceArea						CRITICALITY reject 	TYPE	MBS-ServiceArea							PRESENCE optional   }|
	{ ID id-MBS-CUtoDURRCInformation			CRITICALITY reject	TYPE	MBS-CUtoDURRCInformation				PRESENCE mandatory	}|
	{ ID id-SNSSAI								CRITICALITY reject	TYPE	SNSSAI									PRESENCE mandatory	}|
	{ ID id-BroadcastMRBs-ToBeSetup-List		CRITICALITY reject	TYPE	BroadcastMRBs-ToBeSetup-List		PRESENCE mandatory	}|
	{ ID id-SupportedUETypeList					CRITICALITY ignore	TYPE	SupportedUETypeList						PRESENCE	optional		}|
	{ ID id-AssociatedSessionID					CRITICALITY ignore	TYPE	AssociatedSessionID						PRESENCE optional		}|
	{ ID id-RANSharingAssistanceInformation		CRITICALITY ignore	TYPE	RANSharingAssistanceInformation	PRESENCE optional		},
	...
}

BroadcastMRBs-ToBeSetup-List ::= SEQUENCE (SIZE(1..maxnoofMRBs)) OF ProtocolIE-SingleContainer { { BroadcastMRBs-ToBeSetup-ItemIEs} }


BroadcastMRBs-ToBeSetup-ItemIEs F1AP-PROTOCOL-IES ::= {
	{ ID id-BroadcastMRBs-ToBeSetup-Item	CRITICALITY reject	TYPE 	BroadcastMRBs-ToBeSetup-Item	PRESENCE mandatory	},
	...
}


-- **************************************************************
--
-- BROADCAST CONTEXT SETUP RESPONSE
--
-- **************************************************************

BroadcastContextSetupResponse ::= SEQUENCE {
	protocolIEs			ProtocolIE-Container       { { BroadcastContextSetupResponseIEs} },
	...
}

BroadcastContextSetupResponseIEs F1AP-PROTOCOL-IES ::= {
	{ ID id-gNB-CU-MBS-F1AP-ID					CRITICALITY reject TYPE GNB-CU-MBS-F1AP-ID						PRESENCE mandatory	}|
	{ ID id-gNB-DU-MBS-F1AP-ID					CRITICALITY reject TYPE GNB-DU-MBS-F1AP-ID						PRESENCE mandatory	}|
	{ ID id-BroadcastMRBs-Setup-List			CRITICALITY reject TYPE BroadcastMRBs-Setup-List				PRESENCE mandatory	}|
	{ ID id-BroadcastMRBs-FailedToBeSetup-List	CRITICALITY ignore TYPE BroadcastMRBs-FailedToBeSetup-List	PRESENCE optional	}|
	{ ID id-BroadcastAreaScope					CRITICALITY ignore TYPE BroadcastAreaScope						PRESENCE optional	}|
	{ ID id-CriticalityDiagnostics				CRITICALITY ignore TYPE CriticalityDiagnostics					PRESENCE optional	},
	...
}

BroadcastMRBs-Setup-List ::= SEQUENCE (SIZE(1..maxnoofMRBs)) OF ProtocolIE-SingleContainer { { BroadcastMRBs-Setup-ItemIEs} }

BroadcastMRBs-FailedToBeSetup-List ::= SEQUENCE (SIZE(1..maxnoofMRBs)) OF ProtocolIE-SingleContainer { { BroadcastMRBs-FailedToBeSetup-ItemIEs} }

BroadcastMRBs-Setup-ItemIEs F1AP-PROTOCOL-IES ::= {
	{ ID id-BroadcastMRBs-Setup-Item			CRITICALITY reject	TYPE BroadcastMRBs-Setup-Item			PRESENCE mandatory},
	...
}

BroadcastMRBs-FailedToBeSetup-ItemIEs F1AP-PROTOCOL-IES ::= {
	{ ID id-BroadcastMRBs-FailedToBeSetup-Item	CRITICALITY ignore	TYPE BroadcastMRBs-FailedToBeSetup-Item	PRESENCE mandatory},	...
}


-- **************************************************************
--
-- BROADCAST CONTEXT SETUP FAILURE
--
-- **************************************************************

BroadcastContextSetupFailure ::= SEQUENCE {
	protocolIEs			ProtocolIE-Container       { { BroadcastContextSetupFailureIEs} },
	...
}

BroadcastContextSetupFailureIEs F1AP-PROTOCOL-IES ::= {
	{ ID id-gNB-CU-MBS-F1AP-ID			CRITICALITY reject	TYPE GNB-CU-UE-F1AP-ID			PRESENCE mandatory	}|
	{ ID id-gNB-DU-MBS-F1AP-ID			CRITICALITY ignore	TYPE GNB-DU-UE-F1AP-ID			PRESENCE optional	}|
	{ ID id-Cause						CRITICALITY ignore	TYPE Cause						PRESENCE mandatory	}|
	{ ID id-CriticalityDiagnostics		CRITICALITY ignore	TYPE CriticalityDiagnostics		PRESENCE optional	},
	...
}

-- **************************************************************
--
-- BROADCAST CONTEXT RELEASE ELEMENTARY PROCEDURE
--
-- **************************************************************

-- **************************************************************
--
-- BROADCAST CONTEXT RELEASE COMMAND
--
-- **************************************************************

BroadcastContextReleaseCommand ::= SEQUENCE {
	protocolIEs			ProtocolIE-Container       { { BroadcastContextReleaseCommandIEs} },
	...
}

BroadcastContextReleaseCommandIEs F1AP-PROTOCOL-IES ::= {
	{ ID id-gNB-CU-MBS-F1AP-ID				CRITICALITY reject	TYPE GNB-CU-MBS-F1AP-ID				PRESENCE mandatory	}|
	{ ID id-gNB-DU-MBS-F1AP-ID				CRITICALITY reject	TYPE GNB-DU-MBS-F1AP-ID				PRESENCE mandatory	}|
	{ ID id-Cause							CRITICALITY ignore	TYPE Cause							PRESENCE mandatory	},
	...
}

-- **************************************************************
--
-- BROADCAST CONTEXT RELEASE COMPLETE
--
-- **************************************************************

BroadcastContextReleaseComplete ::= SEQUENCE {
	protocolIEs			ProtocolIE-Container       { { BroadcastContextReleaseCompleteIEs} },
	...
}
BroadcastContextReleaseCompleteIEs F1AP-PROTOCOL-IES ::= {
	{ ID id-gNB-CU-MBS-F1AP-ID			CRITICALITY reject	TYPE GNB-CU-MBS-F1AP-ID			PRESENCE mandatory	}|
	{ ID id-gNB-DU-MBS-F1AP-ID			CRITICALITY reject	TYPE GNB-DU-MBS-F1AP-ID			PRESENCE mandatory	}|
	{ ID id-CriticalityDiagnostics		CRITICALITY ignore	TYPE CriticalityDiagnostics		PRESENCE optional	},
	...
}


-- **************************************************************
--
-- BROADCAST CONTEXT RELEASE REQUEST ELEMENTARY PROCEDURE
--
-- **************************************************************


-- **************************************************************
--
-- BROADCAST CONTEXT RELEASE REQUEST
--
-- **************************************************************

BroadcastContextReleaseRequest ::= SEQUENCE {
	protocolIEs			ProtocolIE-Container       {{ BroadcastContextReleaseRequestIEs}},
	...
}

BroadcastContextReleaseRequestIEs F1AP-PROTOCOL-IES ::= {
	{ ID id-gNB-CU-MBS-F1AP-ID					CRITICALITY reject	TYPE GNB-CU-MBS-F1AP-ID				PRESENCE mandatory	}|
	{ ID id-gNB-DU-MBS-F1AP-ID					CRITICALITY reject	TYPE GNB-DU-MBS-F1AP-ID				PRESENCE mandatory	}|
	{ ID id-Cause								CRITICALITY ignore	TYPE Cause							PRESENCE mandatory	},
	...
}


-- **************************************************************
--
-- BROADCAST CONTEXT MODIFICATION ELEMENTARY PROCEDURE
--
-- **************************************************************

-- **************************************************************
--
-- BROADCAST CONTEXT MODIFICATION REQUEST
--
-- **************************************************************

BroadcastContextModificationRequest ::= SEQUENCE {
	protocolIEs			ProtocolIE-Container       { { BroadcastContextModificationRequestIEs} },
	...
}

BroadcastContextModificationRequestIEs F1AP-PROTOCOL-IES ::= {
	{ ID id-gNB-CU-MBS-F1AP-ID					CRITICALITY reject	TYPE GNB-CU-MBS-F1AP-ID						PRESENCE mandatory	}|
	{ ID id-gNB-DU-MBS-F1AP-ID					CRITICALITY reject	TYPE GNB-DU-MBS-F1AP-ID						PRESENCE mandatory	}|
	{ ID id-MBS-ServiceArea						CRITICALITY reject	TYPE MBS-ServiceArea						PRESENCE optional		}|
	{ ID id-MBS-CUtoDURRCInformation				CRITICALITY reject	TYPE MBS-CUtoDURRCInformation				PRESENCE mandatory	}|
	{ ID id-BroadcastMRBs-ToBeSetupMod-List		CRITICALITY reject	TYPE BroadcastMRBs-ToBeSetupMod-List		PRESENCE optional	}|
	{ ID id-BroadcastMRBs-ToBeModified-List		CRITICALITY reject	TYPE BroadcastMRBs-ToBeModified-List		PRESENCE optional	}|
	{ ID id-BroadcastMRBs-ToBeReleased-List		CRITICALITY reject	TYPE BroadcastMRBs-ToBeReleased-List		PRESENCE optional	}|
	{ ID id-SupportedUETypeList					CRITICALITY ignore	TYPE SupportedUETypeList					PRESENCE	optional	},
	...
}

BroadcastMRBs-ToBeSetupMod-List ::= SEQUENCE (SIZE(1..maxnoofMRBs)) OF ProtocolIE-SingleContainer { { BroadcastMRBs-ToBeSetupMod-ItemIEs} }
BroadcastMRBs-ToBeModified-List ::= SEQUENCE (SIZE(1..maxnoofMRBs)) OF ProtocolIE-SingleContainer { { BroadcastMRBs-ToBeModified-ItemIEs} }
BroadcastMRBs-ToBeReleased-List ::= SEQUENCE (SIZE(1..maxnoofMRBs)) OF ProtocolIE-SingleContainer { { BroadcastMRBs-ToBeReleased-ItemIEs} }

BroadcastMRBs-ToBeSetupMod-ItemIEs F1AP-PROTOCOL-IES ::= {
	{ ID id-BroadcastMRBs-ToBeSetupMod-Item		CRITICALITY reject	TYPE BroadcastMRBs-ToBeSetupMod-Item		PRESENCE mandatory},
	...
}

BroadcastMRBs-ToBeModified-ItemIEs F1AP-PROTOCOL-IES ::= {
	{ ID id-BroadcastMRBs-ToBeModified-Item		CRITICALITY reject	TYPE BroadcastMRBs-ToBeModified-Item		PRESENCE mandatory},
	...
}

BroadcastMRBs-ToBeReleased-ItemIEs F1AP-PROTOCOL-IES ::= {
	{ ID id-BroadcastMRBs-ToBeReleased-Item		CRITICALITY reject	TYPE BroadcastMRBs-ToBeReleased-Item		PRESENCE mandatory},
	...
}


-- **************************************************************
--
-- BROADCAST CONTEXT MODIFICATION RESPONSE
--
-- **************************************************************

BroadcastContextModificationResponse ::= SEQUENCE {
	protocolIEs			ProtocolIE-Container       { { BroadcastContextModificationResponseIEs} },
	...
}


BroadcastContextModificationResponseIEs F1AP-PROTOCOL-IES ::= {
	{ ID id-gNB-CU-MBS-F1AP-ID						CRITICALITY reject TYPE GNB-CU-MBS-F1AP-ID								PRESENCE mandatory}|
	{ ID id-gNB-DU-MBS-F1AP-ID						CRITICALITY reject TYPE GNB-DU-MBS-F1AP-ID								PRESENCE mandatory}|

	{ ID id-BroadcastMRBs-SetupMod-List				CRITICALITY reject TYPE BroadcastMRBs-SetupMod-List					PRESENCE optional}|
	{ ID id-BroadcastMRBs-FailedToBeSetupMod-List	CRITICALITY ignore TYPE BroadcastMRBs-FailedToBeSetupMod-List	PRESENCE optional}|
	{ ID id-BroadcastMRBs-Modified-List				CRITICALITY reject TYPE BroadcastMRBs-Modified-List					PRESENCE optional}|
	{ ID id-BroadcastMRBs-FailedToBeModified-List	CRITICALITY ignore TYPE BroadcastMRBs-FailedToBeModified-List	PRESENCE optional}|
	{ ID id-CriticalityDiagnostics					CRITICALITY ignore	TYPE CriticalityDiagnostics						PRESENCE optional}|
	{ ID id-BroadcastAreaScope						CRITICALITY ignore TYPE BroadcastAreaScope								PRESENCE optional},
	...
}

BroadcastMRBs-SetupMod-List ::= SEQUENCE (SIZE(1..maxnoofMRBs)) OF ProtocolIE-SingleContainer { { BroadcastMRBs-SetupMod-ItemIEs} }

BroadcastMRBs-FailedToBeSetupMod-List ::= SEQUENCE (SIZE(1..maxnoofMRBs)) OF ProtocolIE-SingleContainer { { BroadcastMRBs-FailedToBeSetupMod-ItemIEs} }

BroadcastMRBs-Modified-List::= SEQUENCE (SIZE(1..maxnoofMRBs)) OF ProtocolIE-SingleContainer { { BroadcastMRBs-Modified-ItemIEs } }

BroadcastMRBs-FailedToBeModified-List ::= SEQUENCE (SIZE(1..maxnoofMRBs)) OF ProtocolIE-SingleContainer { { BroadcastMRBs-FailedToBeModified-ItemIEs} }


BroadcastMRBs-SetupMod-ItemIEs F1AP-PROTOCOL-IES ::= {
	{ ID id-BroadcastMRBs-SetupMod-Item				CRITICALITY		reject	TYPE BroadcastMRBs-SetupMod-Item			PRESENCE mandatory},
	...
}

BroadcastMRBs-FailedToBeSetupMod-ItemIEs F1AP-PROTOCOL-IES ::= {
	{ ID id-BroadcastMRBs-FailedToBeSetupMod-Item	CRITICALITY		ignore	TYPE BroadcastMRBs-FailedToBeSetupMod-Item		PRESENCE mandatory},
	...
}

BroadcastMRBs-Modified-ItemIEs F1AP-PROTOCOL-IES ::= {
	{ ID id-BroadcastMRBs-Modified-Item				CRITICALITY		reject	TYPE BroadcastMRBs-Modified-Item			PRESENCE mandatory},
	...
}

BroadcastMRBs-FailedToBeModified-ItemIEs F1AP-PROTOCOL-IES ::= {
	{ ID id-BroadcastMRBs-FailedToBeModified-Item	CRITICALITY 	ignore	TYPE BroadcastMRBs-FailedToBeModified-Item		PRESENCE mandatory},
	...
}

-- **************************************************************
--
-- BROADCAST CONTEXT MODIFICATION FAILURE
--
-- **************************************************************

BroadcastContextModificationFailure ::= SEQUENCE {
	protocolIEs			ProtocolIE-Container       { { BroadcastContextModificationFailureIEs} },
	...
}

BroadcastContextModificationFailureIEs F1AP-PROTOCOL-IES ::= {
	{ ID id-gNB-CU-MBS-F1AP-ID				CRITICALITY reject	TYPE GNB-CU-MBS-F1AP-ID				PRESENCE mandatory	}|
	{ ID id-gNB-DU-MBS-F1AP-ID				CRITICALITY reject	TYPE GNB-DU-MBS-F1AP-ID				PRESENCE mandatory	}|
	{ ID id-Cause							CRITICALITY ignore	TYPE Cause							PRESENCE mandatory	}|
	{ ID id-CriticalityDiagnostics			CRITICALITY ignore	TYPE CriticalityDiagnostics			PRESENCE optional	},
	...
}

-- **************************************************************
--
-- BROADCAST TRANSPORT RESOURCE REQUEST ELEMENTARY PROCEDURE
--
-- **************************************************************


-- **************************************************************
--
-- BROADCAST TRANSPORT RESOURCE REQUEST
--
-- **************************************************************

BroadcastTransportResourceRequest ::= SEQUENCE {
	protocolIEs			ProtocolIE-Container       {{ BroadcastTransportResourceRequestIEs}},
	...
}

BroadcastTransportResourceRequestIEs F1AP-PROTOCOL-IES ::= {
	{ ID id-gNB-CU-MBS-F1AP-ID							CRITICALITY reject	TYPE GNB-CU-MBS-F1AP-ID							PRESENCE mandatory	}|
	{ ID id-gNB-DU-MBS-F1AP-ID							CRITICALITY reject	TYPE GNB-DU-MBS-F1AP-ID							PRESENCE mandatory	}|
	{ ID id-Broadcast-MRBs-Transport-Request-List		CRITICALITY reject 	TYPE Broadcast-MRBs-Transport-Request-List	PRESENCE optional		}|
	{ ID id-F1U-PathFailure								CRITICALITY ignore	TYPE F1U-PathFailure								PRESENCE optional		},
	...
}

Broadcast-MRBs-Transport-Request-List ::= SEQUENCE (SIZE(1..maxnoofMRBs)) OF ProtocolIE-SingleContainer { { Broadcast-MRBs-Transport-Request-ItemIEs} }

Broadcast-MRBs-Transport-Request-ItemIEs F1AP-PROTOCOL-IES ::= {
	{ ID id-Broadcast-MRBs-Transport-Request-Item			CRITICALITY reject	TYPE Broadcast-MRBs-Transport-Request-Item			PRESENCE mandatory},
	...
}


-- **************************************************************
--
-- Multicast Group Paging ELEMENTARY PROCEDURE
--
-- **************************************************************


-- **************************************************************
--
-- Multicast Group Paging
--
-- **************************************************************

MulticastGroupPaging ::= SEQUENCE {
	protocolIEs			ProtocolIE-Container       {{ MulticastGroupPagingIEs}},
	...
}

MulticastGroupPagingIEs F1AP-PROTOCOL-IES ::= {
	{ ID id-MBS-Session-ID					CRITICALITY reject	TYPE MBS-Session-ID							PRESENCE mandatory	}|
	{ ID id-UEIdentity-List-For-Paging-List	CRITICALITY ignore	TYPE UEIdentity-List-For-Paging-List		PRESENCE optional		}|
	{ ID id-MC-PagingCell-List				CRITICALITY ignore	TYPE MC-PagingCell-list						PRESENCE optional		}|
	{ ID id-IndicationMCInactiveReception		CRITICALITY ignore	TYPE IndicationMCInactiveReception		PRESENCE optional		},
	...
}

UEIdentity-List-For-Paging-List	 ::= SEQUENCE (SIZE(1.. maxnoofUEIDforPaging)) OF ProtocolIE-SingleContainer { { UEIdentity-List-For-Paging-ItemIEs } }


UEIdentity-List-For-Paging-ItemIEs F1AP-PROTOCOL-IES ::= {
	{ ID id-UEIdentity-List-For-Paging-Item	CRITICALITY ignore	TYPE UEIdentity-List-For-Paging-Item 			PRESENCE mandatory }	,
	...
}

MC-PagingCell-list::= SEQUENCE (SIZE(1.. maxnoofPagingCells)) OF ProtocolIE-SingleContainer { { MC-PagingCell-ItemIEs } }

MC-PagingCell-ItemIEs F1AP-PROTOCOL-IES ::= {
	{ ID id-MC-PagingCell-Item		CRITICALITY ignore	TYPE MC-PagingCell-Item			PRESENCE mandatory}	,
	...
}



-- **************************************************************
--
-- MULTICAST CONTEXT SETUP ELEMENTARY PROCEDURE
--
-- **************************************************************


-- **************************************************************
--
-- MULTICAST CONTEXT SETUP REQUEST
--
-- **************************************************************

MulticastContextSetupRequest ::= SEQUENCE {
	protocolIEs			ProtocolIE-Container       {{ MulticastContextSetupRequestIEs}},
	...
}

MulticastContextSetupRequestIEs F1AP-PROTOCOL-IES ::= {
	{ ID id-gNB-CU-MBS-F1AP-ID					CRITICALITY reject	TYPE	GNB-CU-MBS-F1AP-ID								PRESENCE mandatory  }|
	{ ID id-MBS-Session-ID						CRITICALITY reject	TYPE	MBS-Session-ID									PRESENCE mandatory  }|
	{ ID id-MBS-ServiceArea						CRITICALITY reject	TYPE	MBS-ServiceArea									PRESENCE optional   }|
	{ ID id-SNSSAI								CRITICALITY reject	TYPE	SNSSAI											PRESENCE mandatory  }|
	{ ID id-MulticastMRBs-ToBeSetup-List			CRITICALITY reject	TYPE	MulticastMRBs-ToBeSetup-List					PRESENCE mandatory  }|
	{ ID id-MulticastCU2DURRCInfo					CRITICALITY reject	TYPE	MulticastCU2DURRCInfo							PRESENCE optional   }|
	{ ID id-MBSMulticastSessionReceptionState		CRITICALITY reject	TYPE	MBSMulticastSessionReceptionState				PRESENCE optional   },
	...
}

MulticastMRBs-ToBeSetup-List ::= SEQUENCE (SIZE(1..maxnoofMRBs)) OF ProtocolIE-SingleContainer { { MulticastMRBs-ToBeSetup-ItemIEs} }


MulticastMRBs-ToBeSetup-ItemIEs F1AP-PROTOCOL-IES ::= {
	{ ID id-MulticastMRBs-ToBeSetup-Item	CRITICALITY reject	TYPE 	MulticastMRBs-ToBeSetup-Item	PRESENCE mandatory	},
	...
}


-- **************************************************************
--
-- MULTICAST CONTEXT SETUP RESPONSE
--
-- **************************************************************

MulticastContextSetupResponse ::= SEQUENCE {
	protocolIEs			ProtocolIE-Container       {{ MulticastContextSetupResponseIEs}},
	...
}

MulticastContextSetupResponseIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-MulticastMRBs-Setup-List			CRITICALITY reject TYPE MulticastMRBs-Setup-List					PRESENCE mandatory	}|
	{ ID id-MulticastMRBs-FailedToBeSetup-List	CRITICALITY ignore TYPE MulticastMRBs-FailedToBeSetup-List 	PRESENCE optional	}|
	{ ID id-CriticalityDiagnostics				CRITICALITY ignore TYPE CriticalityDiagnostics						PRESENCE optional	}|
	{ ID id-MulticastDU2CURRCInfo				CRITICALITY reject TYPE MulticastDU2CURRCInfo						PRESENCE optional	},
	...
}

MulticastMRBs-Setup-List ::= SEQUENCE (SIZE(1..maxnoofMRBs)) OF ProtocolIE-SingleContainer { { MulticastMRBs-Setup-ItemIEs} }

MulticastMRBs-FailedToBeSetup-List ::= SEQUENCE (SIZE(1..maxnoofMRBs)) OF ProtocolIE-SingleContainer { { MulticastMRBs-FailedToBeSetup-ItemIEs} }

MulticastMRBs-Setup-ItemIEs F1AP-PROTOCOL-IES ::= {
	{ ID id-MulticastMRBs-Setup-Item			CRITICALITY reject	TYPE MulticastMRBs-Setup-Item			PRESENCE mandatory},
	...
}

MulticastMRBs-FailedToBeSetup-ItemIEs F1AP-PROTOCOL-IES ::= {
	{ ID id-MulticastMRBs-FailedToBeSetup-Item		CRITICALITY ignore	TYPE MulticastMRBs-FailedToBeSetup-Item	PRESENCE mandatory},
	...
}


-- **************************************************************
--
-- MULTICAST CONTEXT SETUP FAILURE
--
-- **************************************************************

MulticastContextSetupFailure ::= SEQUENCE {
	protocolIEs			ProtocolIE-Container       {{ MulticastContextSetupFailureIEs}},
	...
}

MulticastContextSetupFailureIEs F1AP-PROTOCOL-IES ::= {
	{ ID id-gNB-CU-MBS-F1AP-ID					CRITICALITY reject	TYPE GNB-CU-MBS-F1AP-ID				PRESENCE mandatory	}|
	{ ID id-gNB-DU-MBS-F1AP-ID					CRITICALITY ignore	TYPE GNB-DU-MBS-F1AP-ID				PRESENCE optional	}|
	{ ID id-Cause								CRITICALITY ignore	TYPE Cause							PRESENCE mandatory	}|
	{ ID id-CriticalityDiagnostics				CRITICALITY ignore	TYPE CriticalityDiagnostics			PRESENCE optional	},
	...
}


-- **************************************************************
--
-- MULTICAST CONTEXT RELEASE ELEMENTARY PROCEDURE
--
-- **************************************************************


-- **************************************************************
--
-- MULTICAST CONTEXT RELEASE COMMAND
--
-- **************************************************************

MulticastContextReleaseCommand ::= SEQUENCE {
	protocolIEs			ProtocolIE-Container       {{ MulticastContextReleaseCommandIEs}},
	...
}

MulticastContextReleaseCommandIEs F1AP-PROTOCOL-IES ::= {
	{ ID id-gNB-CU-MBS-F1AP-ID					CRITICALITY reject	TYPE GNB-CU-MBS-F1AP-ID				PRESENCE mandatory	}|
	{ ID id-gNB-DU-MBS-F1AP-ID					CRITICALITY reject	TYPE GNB-DU-MBS-F1AP-ID				PRESENCE mandatory	}|
	{ ID id-Cause								CRITICALITY ignore	TYPE Cause							PRESENCE mandatory	},
	...
}


-- **************************************************************
--
-- MULTICAST CONTEXT RELEASE COMPLETE
--
-- **************************************************************

MulticastContextReleaseComplete ::= SEQUENCE {
	protocolIEs			ProtocolIE-Container       {{ MulticastContextReleaseCompleteIEs}},
	...
}

MulticastContextReleaseCompleteIEs F1AP-PROTOCOL-IES ::= {
	{ ID id-gNB-CU-MBS-F1AP-ID					CRITICALITY reject	TYPE GNB-CU-MBS-F1AP-ID				PRESENCE mandatory	}|
	{ ID id-gNB-DU-MBS-F1AP-ID					CRITICALITY reject	TYPE GNB-DU-MBS-F1AP-ID				PRESENCE mandatory	}|
	{ ID id-CriticalityDiagnostics				CRITICALITY ignore TYPE CriticalityDiagnostics			PRESENCE optional	},
	...
}


-- **************************************************************
--
-- MULTICAST CONTEXT RELEASE REQUEST ELEMENTARY PROCEDURE
--
-- **************************************************************


-- **************************************************************
--
-- MULTICAST CONTEXT RELEASE REQUEST
--
-- **************************************************************

MulticastContextReleaseRequest ::= SEQUENCE {
	protocolIEs			ProtocolIE-Container       {{ MulticastContextReleaseRequestIEs}},
	...
}

MulticastContextReleaseRequestIEs F1AP-PROTOCOL-IES ::= {
	{ ID id-gNB-CU-MBS-F1AP-ID					CRITICALITY reject	TYPE GNB-CU-MBS-F1AP-ID				PRESENCE mandatory	}|
	{ ID id-gNB-DU-MBS-F1AP-ID					CRITICALITY reject	TYPE GNB-DU-MBS-F1AP-ID				PRESENCE mandatory	}|
	{ ID id-Cause								CRITICALITY ignore	TYPE Cause							PRESENCE mandatory	},
	...
}


-- **************************************************************
--
-- MULTICAST CONTEXT MODIFICATION ELEMENTARY PROCEDURE
--
-- **************************************************************


-- **************************************************************
--
-- MULTICAST CONTEXT MODIFICATION REQUEST
--
-- **************************************************************

MulticastContextModificationRequest ::= SEQUENCE {
	protocolIEs			ProtocolIE-Container       {{ MulticastContextModificationRequestIEs}},
	...
}

MulticastContextModificationRequestIEs F1AP-PROTOCOL-IES ::= {
	{ ID id-gNB-CU-MBS-F1AP-ID					CRITICALITY reject	TYPE GNB-CU-MBS-F1AP-ID						PRESENCE mandatory }|
	{ ID id-gNB-DU-MBS-F1AP-ID					CRITICALITY reject	TYPE GNB-DU-MBS-F1AP-ID						PRESENCE mandatory }|
	{ ID id-MBS-ServiceArea						CRITICALITY reject	TYPE MBS-ServiceArea							PRESENCE optional  }|
	{ ID id-MulticastMRBs-ToBeSetupMod-List		CRITICALITY reject	TYPE MulticastMRBs-ToBeSetupMod-List		PRESENCE optional  }|
	{ ID id-MulticastMRBs-ToBeModified-List		CRITICALITY reject	TYPE MulticastMRBs-ToBeModified-List		PRESENCE optional  }|
	{ ID id-MulticastMRBs-ToBeReleased-List		CRITICALITY reject	TYPE MulticastMRBs-ToBeReleased-List		PRESENCE optional  }|
	{ ID id-MulticastCU2DURRCInfo					CRITICALITY reject	TYPE	MulticastCU2DURRCInfo					PRESENCE optional  }|
	{ ID id-MBSMulticastSessionReceptionState		CRITICALITY reject	TYPE MBSMulticastSessionReceptionState		PRESENCE optional  },
	...
}

MulticastMRBs-ToBeSetupMod-List ::= SEQUENCE (SIZE(1..maxnoofMRBs)) OF ProtocolIE-SingleContainer { { MulticastMRBs-ToBeSetupMod-ItemIEs} }
MulticastMRBs-ToBeSetupMod-ItemIEs F1AP-PROTOCOL-IES ::= {
	{ ID id-MulticastMRBs-ToBeSetupMod-Item		CRITICALITY reject	TYPE MulticastMRBs-ToBeSetupMod-Item		PRESENCE mandatory},
	...
}

MulticastMRBs-ToBeModified-List ::= SEQUENCE (SIZE(1..maxnoofMRBs)) OF ProtocolIE-SingleContainer { { MulticastMRBs-ToBeModified-ItemIEs} }
MulticastMRBs-ToBeModified-ItemIEs F1AP-PROTOCOL-IES ::= {
	{ ID id-MulticastMRBs-ToBeModified-Item		CRITICALITY reject	TYPE MulticastMRBs-ToBeModified-Item		PRESENCE mandatory},
	...
}


MulticastMRBs-ToBeReleased-List ::= SEQUENCE (SIZE(1..maxnoofMRBs)) OF ProtocolIE-SingleContainer { { MulticastMRBs-ToBeReleased-ItemIEs} }
MulticastMRBs-ToBeReleased-ItemIEs F1AP-PROTOCOL-IES ::= {
	{ ID id-MulticastMRBs-ToBeReleased-Item		CRITICALITY reject	TYPE MulticastMRBs-ToBeReleased-Item		PRESENCE mandatory},
	...
}


-- **************************************************************
--
-- MULTICAST CONTEXT MODIFICATION RESPONSE
--
-- **************************************************************

MulticastContextModificationResponse ::= SEQUENCE {
	protocolIEs			ProtocolIE-Container       {{ MulticastContextModificationResponseIEs}},
	...
}

MulticastContextModificationResponseIEs F1AP-PROTOCOL-IES ::= {
	{ ID id-gNB-CU-MBS-F1AP-ID						CRITICALITY reject	TYPE GNB-CU-MBS-F1AP-ID								PRESENCE mandatory }|
	{ ID id-gNB-DU-MBS-F1AP-ID						CRITICALITY reject	TYPE GNB-DU-MBS-F1AP-ID								PRESENCE mandatory }|
	{ ID id-MulticastMRBs-SetupMod-List			CRITICALITY reject TYPE MulticastMRBs-SetupMod-List						PRESENCE optional  }|
	{ ID id-MulticastMRBs-FailedToBeSetupMod-List	CRITICALITY ignore TYPE MulticastMRBs-FailedToBeSetupMod-List	PRESENCE optional  }|
	{ ID id-MulticastMRBs-Modified-List			CRITICALITY reject TYPE MulticastMRBs-Modified-List						PRESENCE optional  }|
	{ ID id-MulticastMRBs-FailedToBeModified-List	CRITICALITY ignore TYPE MulticastMRBs-FailedToBeModified-List	PRESENCE optional  }|
	{ ID id-CriticalityDiagnostics					CRITICALITY ignore	TYPE CriticalityDiagnostics						PRESENCE optional  }|
	{ ID id-MulticastDU2CURRCInfo					CRITICALITY reject TYPE MulticastDU2CURRCInfo							PRESENCE optional	},
	...
}

MulticastMRBs-SetupMod-List ::= SEQUENCE (SIZE(1..maxnoofMRBs)) OF ProtocolIE-SingleContainer { { MulticastMRBs-SetupMod-ItemIEs} }
MulticastMRBs-SetupMod-ItemIEs F1AP-PROTOCOL-IES ::= {
	{ ID id-MulticastMRBs-SetupMod-Item				CRITICALITY		reject	TYPE MulticastMRBs-SetupMod-Item			PRESENCE mandatory},
	...
}

MulticastMRBs-FailedToBeSetupMod-List ::= SEQUENCE (SIZE(1..maxnoofMRBs)) OF ProtocolIE-SingleContainer { { MulticastMRBs-FailedToBeSetupMod-ItemIEs} }
MulticastMRBs-FailedToBeSetupMod-ItemIEs F1AP-PROTOCOL-IES ::= {
	{ ID id-MulticastMRBs-FailedToBeSetupMod-Item	CRITICALITY		ignore	TYPE MulticastMRBs-FailedToBeSetupMod-Item		PRESENCE mandatory},
	...
}

MulticastMRBs-Modified-List::= SEQUENCE (SIZE(1..maxnoofMRBs)) OF ProtocolIE-SingleContainer { { MulticastMRBs-Modified-ItemIEs } }
MulticastMRBs-Modified-ItemIEs F1AP-PROTOCOL-IES ::= {
	{ ID id-MulticastMRBs-Modified-Item				CRITICALITY		reject	TYPE MulticastMRBs-Modified-Item			PRESENCE mandatory},
	...
}

MulticastMRBs-FailedToBeModified-List ::= SEQUENCE (SIZE(1..maxnoofMRBs)) OF ProtocolIE-SingleContainer { { MulticastMRBs-FailedToBeModified-ItemIEs} }
MulticastMRBs-FailedToBeModified-ItemIEs F1AP-PROTOCOL-IES ::= {
	{ ID id-MulticastMRBs-FailedToBeModified-Item	CRITICALITY 	ignore	TYPE MulticastMRBs-FailedToBeModified-Item		PRESENCE mandatory},
	...
}


-- **************************************************************
--
-- MULTICAST CONTEXT MODIFICATION FAILURE
--
-- **************************************************************

MulticastContextModificationFailure ::= SEQUENCE {
	protocolIEs			ProtocolIE-Container       {{ MulticastContextModificationFailureIEs}},
	...
}

MulticastContextModificationFailureIEs F1AP-PROTOCOL-IES ::= {
	{ ID id-gNB-CU-MBS-F1AP-ID					CRITICALITY reject	TYPE GNB-CU-MBS-F1AP-ID				PRESENCE mandatory	}|
	{ ID id-gNB-DU-MBS-F1AP-ID					CRITICALITY reject	TYPE GNB-DU-MBS-F1AP-ID				PRESENCE mandatory	}|
	{ ID id-Cause								CRITICALITY ignore	TYPE Cause							PRESENCE mandatory	}|
	{ ID id-CriticalityDiagnostics				CRITICALITY ignore	TYPE CriticalityDiagnostics			PRESENCE optional	},
	...
}


-- **************************************************************
--
-- MULTICAST CONTEXT NOTIFICATION ELEMENTARY PROCEDURE
--
-- **************************************************************


-- **************************************************************
--
-- MULTICAST CONTEXT NOTIFICATION INDICATION
--
-- **************************************************************

MulticastContextNotificationIndication ::= SEQUENCE {
	protocolIEs			ProtocolIE-Container       {{MulticastContextNotificationIndicationIEs}},
	...
}

MulticastContextNotificationIndicationIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-MulticastDU2CURRCInfo				CRITICALITY reject	TYPE MulticastDU2CURRCInfo						PRESENCE optional		},
	...
}


-- **************************************************************
--
-- MULTICAST CONTEXT NOTIFICATION CONFIRM
--
-- **************************************************************

MulticastContextNotificationConfirm ::= SEQUENCE {
	protocolIEs			ProtocolIE-Container       {{MulticastContextNotificationConfirmIEs}},
	...
}

MulticastContextNotificationConfirmIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-CriticalityDiagnostics				CRITICALITY ignore	TYPE CriticalityDiagnostics						PRESENCE optional		},
	...
}


-- **************************************************************
--
-- MULTICAST CONTEXT NOTIFICATION REFUSE
--
-- **************************************************************

MulticastContextNotificationRefuse ::= SEQUENCE {
	protocolIEs			ProtocolIE-Container       {{MulticastContextNotificationRefuseIEs}},
	...
}

MulticastContextNotificationRefuseIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-CriticalityDiagnostics				CRITICALITY ignore	TYPE CriticalityDiagnostics						PRESENCE optional		}|
	{ ID id-Cause								CRITICALITY ignore	TYPE Cause										PRESENCE mandatory	},
	...
}


-- **************************************************************
--
-- MULTICAST COMMON CONFIGURATION ELEMENTARY PROCEDURE
--
-- **************************************************************


-- **************************************************************
--
-- MULTICAST COMMON CONFIGURATION REQUEST
--
-- **************************************************************

MulticastCommonConfigurationRequest ::= SEQUENCE {
	protocolIEs			ProtocolIE-Container       {{MulticastCommonConfigurationRequestIEs}},
	...
}

MulticastCommonConfigurationRequestIEs F1AP-PROTOCOL-IES ::= {
	{ ID id-TransactionID							CRITICALITY reject	TYPE TransactionID											PRESENCE mandatory	}|
	{ ID id-MulticastCU2DUCommonRRCInfo				CRITICALITY reject	TYPE MulticastCU2DUCommonRRCInfo						PRESENCE optional		},
	...
}


-- **************************************************************
--
-- MULTICAST COMMON CONFIGURATION RESPONSE
--
-- **************************************************************

MulticastCommonConfigurationResponse ::= SEQUENCE {
	protocolIEs			ProtocolIE-Container       {{MulticastCommonConfigurationResponseIEs}},
	...
}

MulticastCommonConfigurationResponseIEs F1AP-PROTOCOL-IES ::= {
	{ ID id-TransactionID						CRITICALITY reject	TYPE TransactionID								PRESENCE mandatory	}|
	{ ID id-CriticalityDiagnostics				CRITICALITY ignore	TYPE CriticalityDiagnostics						PRESENCE optional		},
	...
}


-- **************************************************************
--
-- MULTICAST COMMON CONFIGURATION REFUSE
--
-- **************************************************************

MulticastCommonConfigurationRefuse ::= SEQUENCE {
	protocolIEs			ProtocolIE-Container       {{MulticastCommonConfigurationRefuseIEs}},
	...
}

MulticastCommonConfigurationRefuseIEs F1AP-PROTOCOL-IES ::= {
	{ ID id-TransactionID						CRITICALITY reject	TYPE TransactionID								PRESENCE mandatory	}|
	{ ID id-Cause								CRITICALITY ignore	TYPE Cause										PRESENCE mandatory	}|
	{ ID id-CriticalityDiagnostics				CRITICALITY ignore	TYPE CriticalityDiagnostics						PRESENCE optional		},
	...
}


-- **************************************************************
--
-- MULTICAST DISTRIBUTION SETUP ELEMENTARY PROCEDURE
--
-- **************************************************************


-- **************************************************************
--
-- MULTICAST DISTRIBUTION SETUP REQUEST
--
-- **************************************************************

MulticastDistributionSetupRequest ::= SEQUENCE {
	protocolIEs			ProtocolIE-Container       {{ MulticastDistributionSetupRequestIEs}},
	...
}

MulticastDistributionSetupRequestIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-MBSMulticastF1UContextDescriptor	CRITICALITY reject	TYPE MBSMulticastF1UContextDescriptor		PRESENCE mandatory	}|
	{ ID id-MulticastF1UContext-ToBeSetup-List	CRITICALITY reject	TYPE MulticastF1UContext-ToBeSetup-List	PRESENCE mandatory	},
	...
}

MulticastF1UContext-ToBeSetup-List ::= SEQUENCE (SIZE(1..maxnoofMRBs)) OF
																	ProtocolIE-SingleContainer { { MulticastF1UContext-ToBeSetup-ItemIEs} }
MulticastF1UContext-ToBeSetup-ItemIEs F1AP-PROTOCOL-IES ::= {
	{ ID id-MulticastF1UContext-ToBeSetup-Item				CRITICALITY		reject	TYPE MulticastF1UContext-ToBeSetup-Item			PRESENCE mandatory},
	...
}


-- **************************************************************
--
-- MULTICAST DISTRIBUTION SETUP RESPONSE
--
-- **************************************************************

MulticastDistributionSetupResponse ::= SEQUENCE {
	protocolIEs			ProtocolIE-Container       {{ MulticastDistributionSetupResponseIEs}},
	...
}

MulticastDistributionSetupResponseIEs F1AP-PROTOCOL-IES ::= {
	{ ID id-gNB-CU-MBS-F1AP-ID							CRITICALITY reject	TYPE GNB-CU-MBS-F1AP-ID									PRESENCE mandatory}|
	{ ID id-gNB-DU-MBS-F1AP-ID							CRITICALITY reject	TYPE GNB-DU-MBS-F1AP-ID									PRESENCE mandatory}|
	{ ID id-MBSMulticastF1UContextDescriptor			CRITICALITY reject	TYPE MBSMulticastF1UContextDescriptor				PRESENCE mandatory}|
	{ ID id-MulticastF1UContext-Setup-List				CRITICALITY reject	TYPE MulticastF1UContext-Setup-List					PRESENCE mandatory}|
	{ ID id-MulticastF1UContext-FailedToBeSetup-List	CRITICALITY ignore	TYPE MulticastF1UContext-FailedToBeSetup-List		PRESENCE optional}|
	{ ID id-CriticalityDiagnostics						CRITICALITY ignore	TYPE CriticalityDiagnostics								PRESENCE optional }|
	{ ID id-MulticastF1UContextReferenceCU				CRITICALITY reject	TYPE MulticastF1UContextReferenceCU					PRESENCE mandatory},
	...
}

MulticastF1UContext-Setup-List ::= SEQUENCE (SIZE(1..maxnoofMRBs)) OF ProtocolIE-SingleContainer { { MulticastF1UContext-Setup-ItemIEs} }
MulticastF1UContext-Setup-ItemIEs F1AP-PROTOCOL-IES ::= {
	{ ID id-MulticastF1UContext-Setup-Item				CRITICALITY		reject	TYPE MulticastF1UContext-Setup-Item			PRESENCE mandatory},
	...
}

MulticastF1UContext-FailedToBeSetup-List ::= SEQUENCE (SIZE(1..maxnoofMRBs)) OF
																ProtocolIE-SingleContainer { { MulticastF1UContext-FailedToBeSetup-ItemIEs} }
MulticastF1UContext-FailedToBeSetup-ItemIEs F1AP-PROTOCOL-IES ::= {
	{ ID id-MulticastF1UContext-FailedToBeSetup-Item	CRITICALITY	 ignore	TYPE MulticastF1UContext-FailedToBeSetup-Item	 PRESENCE mandatory},
	...
}


-- **************************************************************
--
-- MULTICAST DISTRIBUTION SETUP FAILURE
--
-- **************************************************************

MulticastDistributionSetupFailure ::= SEQUENCE {
	protocolIEs			ProtocolIE-Container       {{ MulticastDistributionSetupFailureIEs}},
	...
}

MulticastDistributionSetupFailureIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY ignore	TYPE GNB-DU-MBS-F1AP-ID							PRESENCE optional	}|
	{ ID id-MBSMulticastF1UContextDescriptor	CRITICALITY reject	TYPE MBSMulticastF1UContextDescriptor		PRESENCE mandatory	}|
	{ ID id-Cause								CRITICALITY ignore	TYPE Cause										PRESENCE mandatory	}|
	{ ID id-CriticalityDiagnostics				CRITICALITY ignore	TYPE CriticalityDiagnostics						PRESENCE optional	},
	...
}


-- **************************************************************
--
-- MULTICAST DISTRIBUTION RELEASE ELEMENTARY PROCEDURE
--
-- **************************************************************


-- **************************************************************
--
-- MULTICAST DISTRIBUTION RELEASE COMMAND
--
-- **************************************************************

MulticastDistributionReleaseCommand ::= SEQUENCE {
	protocolIEs			ProtocolIE-Container       {{ MulticastDistributionReleaseCommandIEs}},
	...
}

MulticastDistributionReleaseCommandIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-MBSMulticastF1UContextDescriptor	CRITICALITY reject	TYPE MBSMulticastF1UContextDescriptor		PRESENCE mandatory	}|
	{ ID id-Cause								CRITICALITY ignore	TYPE Cause										PRESENCE mandatory	},
	...
}


-- **************************************************************
--
-- MULTICAST DISTRIBUTION RELEASE COMPLETE
--
-- **************************************************************

MulticastDistributionReleaseComplete ::= SEQUENCE {
	protocolIEs			ProtocolIE-Container       {{ MulticastDistributionReleaseCompleteIEs}},
	...
}

MulticastDistributionReleaseCompleteIEs F1AP-PROTOCOL-IES ::= {
	{ ID id-gNB-CU-MBS-F1AP-ID					CRITICALITY reject	TYPE GNB-CU-MBS-F1AP-ID							PRESENCE mandatory	}|
	{ ID id-gNB-DU-MBS-F1AP-ID					CRITICALITY reject	TYPE GNB-DU-MBS-F1AP-ID							PRESENCE mandatory	}|
	{ ID id-MBSMulticastF1UContextDescriptor	CRITICALITY reject	TYPE MBSMulticastF1UContextDescriptor		PRESENCE mandatory	}|
	{ ID id-CriticalityDiagnostics				CRITICALITY ignore	TYPE CriticalityDiagnostics						PRESENCE optional	},
	...
}


-- **************************************************************
--
-- PDC MEASUREMENT ELEMENTARY PROCEDURE
--
-- **************************************************************

-- **************************************************************
--
-- PDC Measurement Initiation Request
--
-- **************************************************************

PDCMeasurementInitiationRequest ::= SEQUENCE {
	protocolIEs		ProtocolIE-Container	{{PDCMeasurementInitiationRequest-IEs}},
	...
}

PDCMeasurementInitiationRequest-IEs F1AP-PROTOCOL-IES ::= {
	{ ID id-gNB-CU-UE-F1AP-ID				CRITICALITY reject	TYPE GNB-CU-UE-F1AP-ID					PRESENCE mandatory	}|
	{ ID id-gNB-DU-UE-F1AP-ID				CRITICALITY reject	TYPE GNB-DU-UE-F1AP-ID					PRESENCE mandatory	}|
	{ ID id-RAN-UE-PDC-MeasID				CRITICALITY reject	TYPE RAN-UE-PDC-MeasID					PRESENCE mandatory	}|
	{ ID id-PDCReportType					CRITICALITY reject	TYPE PDCReportType						PRESENCE mandatory	}|
	{ ID id-PDCMeasurementPeriodicity		CRITICALITY reject	TYPE PDCMeasurementPeriodicity			PRESENCE conditional	}|
	-- The above IE shall be present if the PDCReportType IE is set to "periodic" --
	{ ID id-PDCMeasurementQuantities		CRITICALITY reject	TYPE PDCMeasurementQuantities			PRESENCE mandatory	},
	...
}

-- **************************************************************
--
-- PDC Measurement Initiation Response
--
-- **************************************************************

PDCMeasurementInitiationResponse ::= SEQUENCE {
	protocolIEs		ProtocolIE-Container	{{PDCMeasurementInitiationResponse-IEs}},
	...
}

PDCMeasurementInitiationResponse-IEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-RAN-UE-PDC-MeasID			CRITICALITY reject	TYPE RAN-UE-PDC-MeasID			PRESENCE mandatory	}|
	{ ID id-PDCMeasurementResult		CRITICALITY ignore	TYPE PDCMeasurementResult		PRESENCE optional		}|
	{ ID id-CriticalityDiagnostics		CRITICALITY ignore	TYPE CriticalityDiagnostics		PRESENCE optional		},
	...
}

-- **************************************************************
--
-- PDC Measurement Initiation Failure
--
-- **************************************************************

PDCMeasurementInitiationFailure ::= SEQUENCE {
	protocolIEs						ProtocolIE-Container		{{PDCMeasurementInitiationFailure-IEs}},
	...
}

PDCMeasurementInitiationFailure-IEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-RAN-UE-PDC-MeasID			CRITICALITY ignore	TYPE RAN-UE-PDC-MeasID				PRESENCE mandatory	}|
	{ ID id-Cause						CRITICALITY ignore	TYPE Cause							PRESENCE mandatory	}|
	{ ID id-CriticalityDiagnostics		CRITICALITY ignore	TYPE CriticalityDiagnostics			PRESENCE optional	},
	...
}

-- **************************************************************
--
-- PDC MEASUREMENT REPORT ELEMENTARY PROCEDURE
--
-- **************************************************************

-- **************************************************************
--
-- PDC Measurement Report
--
-- **************************************************************

PDCMeasurementReport ::= SEQUENCE {
	protocolIEs						ProtocolIE-Container		{{PDCMeasurementReport-IEs}},
	...
}

PDCMeasurementReport-IEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-RAN-UE-PDC-MeasID			CRITICALITY reject	TYPE RAN-UE-PDC-MeasID			PRESENCE mandatory	}|
	{ ID id-PDCMeasurementResult		CRITICALITY ignore	TYPE PDCMeasurementResult		PRESENCE mandatory	},
	...
}

-- **************************************************************
--
-- PDC MEASUREMENT TERMINATION PROCEDURE
--
-- **************************************************************

-- **************************************************************
--
-- PDC Measurement Termination
--
-- **************************************************************

PDCMeasurementTerminationCommand ::= SEQUENCE {
	protocolIEs		ProtocolIE-Container		{ { PDCMeasurementTerminationCommand-IEs} },
	...
}


PDCMeasurementTerminationCommand-IEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-RAN-UE-PDC-MeasID			CRITICALITY	ignore	TYPE RAN-UE-PDC-MeasID			PRESENCE mandatory	},
	...
}


-- **************************************************************
--
-- PDC MEASUREMENT FAILURE INDICATION ELEMENTARY PROCEDURE
--
-- **************************************************************

-- **************************************************************
--
-- PDC Measurement Failure Indication
--
-- **************************************************************


PDCMeasurementFailureIndication ::= SEQUENCE {
	protocolIEs		ProtocolIE-Container		{ { PDCMeasurementFailureIndication-IEs} },
	...
}

PDCMeasurementFailureIndication-IEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-RAN-UE-PDC-MeasID			CRITICALITY ignore	TYPE RAN-UE-PDC-MeasID			PRESENCE mandatory	}|
	{ ID id-Cause						CRITICALITY ignore	TYPE Cause						PRESENCE mandatory	},
	...
}

-- **************************************************************
--
-- PPS CONFIGURATION ELEMENTARY PROCEDURE
--
-- **************************************************************

-- **************************************************************
--
-- PRS CONFIGURATION REQUEST
--
-- **************************************************************

PRSConfigurationRequest ::= SEQUENCE {
	protocolIEs		ProtocolIE-Container	{{PRSConfigurationRequest-IEs}},
	...
}

PRSConfigurationRequest-IEs F1AP-PROTOCOL-IES ::= {
	{ ID id-TransactionID			CRITICALITY reject	TYPE TransactionID						PRESENCE mandatory }|
	{ ID id-PRSConfigRequestType	CRITICALITY reject	TYPE PRSConfigRequestType				PRESENCE mandatory }|
	{ ID id-PRSTRPList				CRITICALITY ignore	TYPE PRSTRPList							PRESENCE mandatory },
	...
}

-- **************************************************************
--
-- PRS CONFIGURATION RESPONSE
--
-- **************************************************************

PRSConfigurationResponse ::= SEQUENCE {
	protocolIEs		ProtocolIE-Container	{{ PRSConfigurationResponse-IEs}},
	...
}

PRSConfigurationResponse-IEs F1AP-PROTOCOL-IES ::= {
	{ ID id-TransactionID			CRITICALITY reject	TYPE TransactionID					PRESENCE mandatory}|
	{ ID id-PRSTransmissionTRPList	CRITICALITY ignore	TYPE PRSTransmissionTRPList			PRESENCE optional}|
	{ ID id-CriticalityDiagnostics	CRITICALITY ignore	TYPE CriticalityDiagnostics			PRESENCE optional},
	...
}

-- **************************************************************
--
-- PRS CONFIGURATION FAILURE
--
-- **************************************************************

PRSConfigurationFailure ::= SEQUENCE {
	protocolIEs		ProtocolIE-Container	{{ PRSConfigurationFailure-IEs}},
	...
}

PRSConfigurationFailure-IEs F1AP-PROTOCOL-IES ::= {
	{ ID id-TransactionID			CRITICALITY reject	TYPE TransactionID				PRESENCE mandatory}|
	{ ID id-Cause	CRITICALITY ignore	TYPE Cause	PRESENCE mandatory}|
	{ ID id-CriticalityDiagnostics	CRITICALITY ignore	TYPE CriticalityDiagnostics		PRESENCE optional},
	...
}


-- **************************************************************
--
-- MEASUREMENT PRECONFIGURATION ELEMENTARY PROCEDURE
--
-- **************************************************************

-- **************************************************************
--
-- Positioning Preconfiguration Required
--
-- **************************************************************

MeasurementPreconfigurationRequired ::= SEQUENCE {
	protocolIEs		ProtocolIE-Container	{{ MeasurementPreconfigurationRequired-IEs}},
	...
}

MeasurementPreconfigurationRequired-IEs F1AP-PROTOCOL-IES ::= {
	{ ID id-gNB-CU-UE-F1AP-ID	CRITICALITY reject	TYPE GNB-CU-UE-F1AP-ID	PRESENCE mandatory}|
	{ ID id-gNB-DU-UE-F1AP-ID	CRITICALITY reject	TYPE GNB-DU-UE-F1AP-ID	PRESENCE mandatory}|
	{ ID id-TRP-PRS-Info-List	CRITICALITY ignore	TYPE TRP-PRS-Info-List	PRESENCE mandatory},
	...
}


-- **************************************************************
--
-- Positioning Preconfiguration Confirm
--
-- **************************************************************

MeasurementPreconfigurationConfirm ::= SEQUENCE {
	protocolIEs			ProtocolIE-Container       { { MeasurementPreconfigurationConfirm-IEs} },
	...
}


MeasurementPreconfigurationConfirm-IEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-PosMeasGapPreConfigList		CRITICALITY ignore	TYPE PosMeasGapPreConfigList		PRESENCE optional }|
	{ ID id-CriticalityDiagnostics		CRITICALITY ignore	TYPE CriticalityDiagnostics			PRESENCE optional },
	...
}




-- **************************************************************
--
-- Positioning Preconfiguration Refuse
--
-- **************************************************************

MeasurementPreconfigurationRefuse ::= SEQUENCE {
	protocolIEs			ProtocolIE-Container       { { MeasurementPreconfigurationRefuse-IEs} },
	...
}

MeasurementPreconfigurationRefuse-IEs F1AP-PROTOCOL-IES ::= {
	{ ID id-gNB-CU-UE-F1AP-ID			CRITICALITY reject	TYPE GNB-CU-UE-F1AP-ID			PRESENCE mandatory	}|
	{ ID id-gNB-DU-UE-F1AP-ID			CRITICALITY reject	TYPE GNB-DU-UE-F1AP-ID			PRESENCE mandatory	}|
	{ ID id-Cause						CRITICALITY ignore	TYPE Cause						PRESENCE mandatory	}|
	{ ID id-CriticalityDiagnostics		CRITICALITY ignore	TYPE CriticalityDiagnostics		PRESENCE optional },
	...
}


-- **************************************************************
--
-- MEASUREMENT ACTIVATION ELEMENTARY PROCEDURE
--
-- **************************************************************

-- **************************************************************
--
-- Measurement Activation
--
-- **************************************************************

MeasurementActivation ::= SEQUENCE {
	protocolIEs			ProtocolIE-Container       { { MeasurementActivation-IEs} },
	...
}

MeasurementActivation-IEs F1AP-PROTOCOL-IES ::= {
	{ ID id-gNB-CU-UE-F1AP-ID			CRITICALITY reject	TYPE GNB-CU-UE-F1AP-ID				PRESENCE mandatory	}|
	{ ID id-gNB-DU-UE-F1AP-ID			CRITICALITY reject	TYPE GNB-DU-UE-F1AP-ID				PRESENCE mandatory	}|
	{ ID id-ActivationRequestType		CRITICALITY reject	TYPE ActivationRequestType 			PRESENCE mandatory}|
	{ ID id-PRS-Measurement-Info-List	CRITICALITY ignore	TYPE PRS-Measurement-Info-List		PRESENCE optional},
	...
}

-- **************************************************************
--
-- QOE INFORMATION TRANSFER ELEMENTARY PROCEDURE
--
-- **************************************************************

-- **************************************************************
--
-- QoE Information Transfer
--
-- **************************************************************


QoEInformationTransfer ::= SEQUENCE {
	protocolIEs						ProtocolIE-Container		{{QoEInformationTransfer-IEs}},
	...
}


QoEInformationTransfer-IEs F1AP-PROTOCOL-IES ::= {
	{ ID id-gNB-CU-UE-F1AP-ID			CRITICALITY reject	TYPE GNB-CU-UE-F1AP-ID					PRESENCE mandatory	}|
	{ ID id-gNB-DU-UE-F1AP-ID			CRITICALITY reject	TYPE GNB-DU-UE-F1AP-ID					PRESENCE mandatory	}|
	{ ID id-QoEInformation				CRITICALITY ignore	TYPE QoEInformation						PRESENCE optional	},
	...
}


-- **************************************************************
--
-- POSITIONING SYSTEM INFORMATION DELIVERY ELEMENTARY PROCEDURE
--
-- **************************************************************

-- **************************************************************
--
-- Positioning System information Delivery Command
--
-- **************************************************************

PosSystemInformationDeliveryCommand ::= SEQUENCE {
	protocolIEs			ProtocolIE-Container       {{ PosSystemInformationDeliveryCommandIEs}},
	...
}

PosSystemInformationDeliveryCommandIEs F1AP-PROTOCOL-IES ::= {
	{ ID id-TransactionID			CRITICALITY reject	TYPE TransactionID					PRESENCE mandatory	}|
	{ ID id-NRCGI					CRITICALITY reject	TYPE NRCGI							PRESENCE mandatory	}|
	{ ID id-PosSItypeList			CRITICALITY reject	TYPE PosSItypeList					PRESENCE mandatory	}|
	{ ID id-ConfirmedUEID 			CRITICALITY reject	TYPE GNB-DU-UE-F1AP-ID				PRESENCE mandatory	},
	...
}

-- **************************************************************
--
-- DU-CU CELL SWITCH NOTIFICATION ELEMENTARY PROCEDURE
--
-- **************************************************************

-- **************************************************************
--
-- DU-CU Cell Switch Notification
--
-- **************************************************************

DUCUCellSwitchNotification ::= SEQUENCE {
	protocolIEs			ProtocolIE-Container       {{ DUCUCellSwitchNotificationIEs}},
	...
}

DUCUCellSwitchNotificationIEs F1AP-PROTOCOL-IES ::= {
	{ ID id-gNB-CU-UE-F1AP-ID		CRITICALITY reject	TYPE GNB-CU-UE-F1AP-ID				PRESENCE mandatory	}|
	{ ID id-gNB-DU-UE-F1AP-ID		CRITICALITY reject	TYPE GNB-DU-UE-F1AP-ID				PRESENCE mandatory	}|
	{ ID id-NRCGI					CRITICALITY reject	TYPE NRCGI							PRESENCE mandatory	}|
	{ ID id-LTMCellSwitchInformation	 CRITICALITY ignore	TYPE LTMCellSwitchInformation	PRESENCE optional		}|
	{ ID id-TAInformation-List			CRITICALITY ignore	TYPE TAInformation-List			PRESENCE optional		},
	...
}


-- **************************************************************
--
-- CU-DU CELL SWITCH NOTIFICATION ELEMENTARY PROCEDURE
--
-- **************************************************************

-- **************************************************************
--
-- CU-DU Cell Switch Notification
--
-- **************************************************************

CUDUCellSwitchNotification ::= SEQUENCE {
	protocolIEs			ProtocolIE-Container       {{ CUDUCellSwitchNotificationIEs}},
	...
}

CUDUCellSwitchNotificationIEs F1AP-PROTOCOL-IES ::= {
	{ ID id-gNB-CU-UE-F1AP-ID		CRITICALITY reject	TYPE GNB-CU-UE-F1AP-ID				PRESENCE mandatory	}|
	{ ID id-gNB-DU-UE-F1AP-ID		CRITICALITY reject	TYPE GNB-DU-UE-F1AP-ID				PRESENCE mandatory	}|
	{ ID id-NRCGI					CRITICALITY reject	TYPE NRCGI							PRESENCE mandatory	}|
	{ ID id-LTMCellSwitchInformation	 CRITICALITY ignore	TYPE LTMCellSwitchInformation	PRESENCE optional	}|
	{ ID id-TAInformation-List			CRITICALITY ignore	TYPE TAInformation-List			PRESENCE optional		}|
	{ ID id-LastVisitedLTMCells			CRITICALITY ignore	TYPE LastVisitedLTMCells			PRESENCE optional		},
	...
}


-- **************************************************************
--
-- DU-CU TA INFORMATION TRANSFER ELEMENTARY PROCEDURE
--
-- **************************************************************

-- **************************************************************
--
-- DU-CU TA Information Transfer
--
-- **************************************************************

DUCUTAInformationTransfer ::= SEQUENCE {
	protocolIEs			ProtocolIE-Container       {{ DUCUTAInformationTransferIEs}},
	...
}

DUCUTAInformationTransferIEs F1AP-PROTOCOL-IES ::= {
	{ ID id-TransactionID					CRITICALITY reject	TYPE TransactionID							PRESENCE mandatory	}|
	{ ID id-DUtoCUTAInformation-List		CRITICALITY ignore	TYPE DUtoCUTAInformation-List				PRESENCE mandatory	},
	...
}

-- **************************************************************
--
-- CU-DU TA INFORMATION TRANSFER ELEMENTARY PROCEDURE
--
-- **************************************************************

-- **************************************************************
--
-- CU-DU TA Information Transfer
--
-- **************************************************************

CUDUTAInformationTransfer ::= SEQUENCE {
	protocolIEs			ProtocolIE-Container       {{ CUDUTAInformationTransferIEs}},
	...
}

CUDUTAInformationTransferIEs F1AP-PROTOCOL-IES ::= {
	{ ID id-TransactionID					CRITICALITY reject	TYPE TransactionID					PRESENCE mandatory	}|
	{ ID id-CUtoDUTAInformation-List		CRITICALITY ignore	TYPE CUtoDUTAInformation-List				PRESENCE mandatory	},
	...
}

-- **************************************************************
--
-- QOE INFORMATION TRANSFER CONTROL ELEMENTARY PROCEDURE
--
-- **************************************************************

-- **************************************************************
--
-- QoE Information Transfer Control
--
-- **************************************************************


QoEInformationTransferControl ::= SEQUENCE {
	protocolIEs						ProtocolIE-Container {{QoEInformationTransferControl-IEs}},
	...
}


QoEInformationTransferControl-IEs F1AP-PROTOCOL-IES ::= {
	{ ID id-TransactionID						CRITICALITY reject	TYPE TransactionID								PRESENCE mandatory	}|
	{ ID id-DeactivationIndication				CRITICALITY ignore	TYPE DeactivationIndication						PRESENCE optional	},
	...
}


-- **************************************************************
--
-- RACH Indication ELEMENTARY PROCEDURE
--
-- **************************************************************

-- **************************************************************
--
-- RACH Indication
--
-- **************************************************************


RachIndication ::= SEQUENCE {
	protocolIEs						ProtocolIE-Container		{{ RachIndication-IEs}},
	...
}


RachIndication-IEs F1AP-PROTOCOL-IES ::= {
	{ ID id-TransactionID				CRITICALITY reject	TYPE TransactionID				PRESENCE mandatory	}|
	{ ID id-RAReportIndicationList				CRITICALITY reject	TYPE RAReportIndicationList						PRESENCE mandatory	},
	...
}

-- **************************************************************
--
-- Timing Synchronisation Status Elementary Procedure
--
-- **************************************************************

-- **************************************************************
--
-- TIMING SYNCHRONISATION STATUS REQUEST
--
-- **************************************************************

TimingSynchronisationStatusRequest::= SEQUENCE {
	protocolIEs		ProtocolIE-Container	{{TimingSynchronisationStatusRequest-IEs}},
	...
}

TimingSynchronisationStatusRequest-IEs F1AP-PROTOCOL-IES ::= {
	{ ID id-TransactionID					CRITICALITY reject	TYPE TransactionID								PRESENCE mandatory	}|
	{ ID id-RANTSSRequestType				CRITICALITY reject	TYPE RANTSSRequestType							PRESENCE mandatory },
	...
}

-- **************************************************************
--
-- TIMING SYNCHRONISATION STATUS RESPONSE
--
-- **************************************************************

TimingSynchronisationStatusResponse::= SEQUENCE {
	protocolIEs		ProtocolIE-Container	{{TimingSynchronisationStatusResponse-IEs}},
	...
}

TimingSynchronisationStatusResponse-IEs F1AP-PROTOCOL-IES ::= {
	{ ID id-TransactionID				CRITICALITY reject	TYPE TransactionID					PRESENCE mandatory	}|
	{ ID id-CriticalityDiagnostics		CRITICALITY ignore	TYPE CriticalityDiagnostics			PRESENCE optional	},
	...
}

-- **************************************************************
--
-- TIMING SYNCHRONISATION STATUS FAILURE
--
-- **************************************************************

TimingSynchronisationStatusFailure::= SEQUENCE {
	protocolIEs		ProtocolIE-Container	{{TimingSynchronisationStatusFailure-IEs}},
	...
}

TimingSynchronisationStatusFailure-IEs F1AP-PROTOCOL-IES ::= {
	{ ID id-TransactionID						CRITICALITY reject	TYPE TransactionID					PRESENCE mandatory	}|
	{ ID id-Cause								CRITICALITY ignore	TYPE Cause							PRESENCE mandatory	}|
	{ ID id-CriticalityDiagnostics				CRITICALITY ignore	TYPE CriticalityDiagnostics			PRESENCE optional	},
	...
}
-- **************************************************************
--
-- Timing Synchronisation Status Reporting Elementary Procedure
--
-- **************************************************************

-- **************************************************************
--
-- TIMING SYNCHRONISATION STATUS REPORT
--
-- **************************************************************

TimingSynchronisationStatusReport::= SEQUENCE {
	protocolIEs		ProtocolIE-Container	{{ TimingSynchronisationStatusReport-IEs}},
	...
}

TimingSynchronisationStatusReport-IEs F1AP-PROTOCOL-IES ::= {
	{ ID id-TransactionID									CRITICALITY reject	TYPE TransactionID						PRESENCE mandatory	}|
	{ ID id-RANTimingSynchronisationStatusInfo				CRITICALITY ignore	TYPE RANTimingSynchronisationStatusInfo							PRESENCE mandatory },
	...
}

-- **************************************************************
--
--  DU-CU Access And Mobility Indication ELEMENTARY PROCEDURE
--
-- **************************************************************

-- **************************************************************
--
-- DU-CU Access And Mobility Indication
--
-- **************************************************************

DUCUAccessAndMobilityIndication ::= SEQUENCE {
	protocolIEs			ProtocolIE-Container       { { DUCUAccessAndMobilityIndicationIEs} },
	...
}

DUCUAccessAndMobilityIndicationIEs F1AP-PROTOCOL-IES ::= {
	{ ID id-TransactionID							CRITICALITY reject	TYPE TransactionID						PRESENCE mandatory }|
	{ ID id-DLLBTFailureInformationList				CRITICALITY ignore	TYPE DLLBTFailureInformationList	PRESENCE optional}|
	{ ID id-MROForLTM-Information		CRITICALITY ignore	TYPE MROForLTM-Information	PRESENCE optional },
	...
}


-- **************************************************************
--
-- CU-DU MOBILITY INITIATION ELEMENTARY PROCEDURE
--
-- **************************************************************

-- **************************************************************
--
-- CU-DU Mobility Initiation Request
--
-- **************************************************************

CUDUMobilityInitiationRequest ::= SEQUENCE {
	protocolIEs			ProtocolIE-Container       {{ CUDUMobilityInitiationRequestIEs }},
	...
}

CUDUMobilityInitiationRequestIEs F1AP-PROTOCOL-IES ::= {
	{ ID id-gNB-CU-UE-F1AP-ID		CRITICALITY reject	TYPE GNB-CU-UE-F1AP-ID				PRESENCE mandatory	}|
	{ ID id-gNB-DU-UE-F1AP-ID		CRITICALITY reject	TYPE GNB-DU-UE-F1AP-ID				PRESENCE mandatory	}|
	{ ID id-MobilityInitiation		CRITICALITY reject	TYPE MobilityInitiation				PRESENCE mandatory	},
	...
}

-- **************************************************************
--
-- CLI Indication
--
-- **************************************************************

CLI-Indication ::= SEQUENCE {
	protocolIEs		ProtocolIE-Container	{{CLI-Indication-IEs}},
	...
}

CLI-Indication-IEs F1AP-PROTOCOL-IES ::= {
	{ ID id-TransactionID							CRITICALITY reject	TYPE TransactionID						PRESENCE mandatory }|
	{ ID id-CLI-MeasurementResult-List					CRITICALITY ignore	TYPE CLI-MeasurementResult-List							PRESENCE optional }|
	{ ID id-SRS-Resource-Indication					CRITICALITY ignore	TYPE SRS-Resource-Indication			PRESENCE optional },
	...
}



-- **************************************************************
--
-- DU-CU CSI-RS COORDINATION ELEMENTARY PROCEDURE
--
-- **************************************************************

-- **************************************************************
--
-- DU-CU CSI-RS COORDINATION REQUEST
--
-- **************************************************************
DUCUCSIRSCoordinationRequest ::= SEQUENCE {
	protocolIEs			ProtocolIE-Container       { {DUCUCSIRSCoordinationRequest-IEs} },
	...
}

DUCUCSIRSCoordinationRequest-IEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY reject	TYPE GNB-DU-UE-F1AP-ID									PRESENCE mandatory 	}|
	{ ID id-CSI-RSCoordinationRequestList				CRITICALITY ignore	TYPE CSI-RSCoordinationRequestList						PRESENCE mandatory},
	...
}


-- **************************************************************
--
-- DU-CU CSI-RS COORDINATION RESPONSE
--
-- **************************************************************

DUCUCSIRSCoordinationResponse ::= SEQUENCE {
	protocolIEs			ProtocolIE-Container       { {DUCUCSIRSCoordinationResponse-IEs} },
	...
}


DUCUCSIRSCoordinationResponse-IEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY reject	TYPE GNB-DU-UE-F1AP-ID									PRESENCE mandatory	}|
	{ ID id-CSI-RSCoordinationResultList			CRITICALITY ignore	TYPE CSI-RSCoordinationResultList					PRESENCE mandatory},
	...
}


-- **************************************************************
--
-- CU-DU CSI-RS COORDINATION ELEMENTARY PROCEDURE
--
-- **************************************************************

-- **************************************************************
--
-- CU-DU CSI-RS COORDINATION REQUEST
--
-- **************************************************************

CUDUCSIRSCoordinationRequest::= SEQUENCE {
	protocolIEs			ProtocolIE-Container       { {CUDUCSIRSCoordinationRequest-IEs} },
	...
}

CUDUCSIRSCoordinationRequest-IEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY reject	TYPE GNB-DU-UE-F1AP-ID									PRESENCE mandatory	}|
	{ ID id-CSI-RSCoordinationRequestList			CRITICALITY ignore	TYPE CSI-RSCoordinationRequestList					PRESENCE mandatory},
	...
}


-- **************************************************************
--
-- CU-DU CSI-RS COORDINATION RESPONSE
--
-- **************************************************************

CUDUCSIRSCoordinationResponse ::= SEQUENCE {
	protocolIEs			ProtocolIE-Container       { {CUDUCSIRSCoordinationResponse-IEs} },
	...
}


CUDUCSIRSCoordinationResponse-IEs F1AP-PROTOCOL-IES ::= {
	{ ID id-gNB-CU-UE-F1AP-ID						CRITICALITY reject	TYPE GNB-CU-UE-F1AP-ID									PRESENCE mandatory	}|
	{ ID id-gNB-DU-UE-F1AP-ID						CRITICALITY reject	TYPE GNB-DU-UE-F1AP-ID									PRESENCE mandatory 	}|
	{ ID id-CSI-RSCoordinationResultList			CRITICALITY ignore	TYPE CSI-RSCoordinationResultList					PRESENCE mandatory},
	...
}



END

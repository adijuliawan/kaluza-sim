-- Extracted by spec/tools/docx_asn1.py 1.0 from 3GPP TS 37.483 j40 (37483-j40.zip, sha256 fc24be828df5709761f7da1806a51b1ddb9a68ee7e21a70efc92b1c19fa56987).
-- Do not edit: regenerate with spec/tools/docx_asn1.py. Text (c) 3GPP; see spec/INDEX.tsv for the source.

E1AP-Constants {
itu-t (0) identified-organization (4) etsi (0) mobileDomain (0)
ngran-access (22) modules (3) e1ap (5) version1 (1) e1ap-Constants (4) }

DEFINITIONS AUTOMATIC TAGS ::=

BEGIN

IMPORTS

	ProcedureCode,
	ProtocolIE-ID

FROM E1AP-CommonDataTypes;

-- **************************************************************
--
-- Elementary Procedures
--
-- **************************************************************

id-reset														ProcedureCode ::= 0
id-errorIndication												ProcedureCode ::= 1
id-privateMessage												ProcedureCode ::= 2
id-gNB-CU-UP-E1Setup											ProcedureCode ::= 3
id-gNB-CU-CP-E1Setup											ProcedureCode ::= 4
id-gNB-CU-UP-ConfigurationUpdate								ProcedureCode ::= 5
id-gNB-CU-CP-ConfigurationUpdate								ProcedureCode ::= 6
id-e1Release													ProcedureCode ::= 7
id-bearerContextSetup											ProcedureCode ::= 8
id-bearerContextModification									ProcedureCode ::= 9
id-bearerContextModificationRequired							ProcedureCode ::= 10
id-bearerContextRelease											ProcedureCode ::= 11
id-bearerContextReleaseRequest									ProcedureCode ::= 12
id-bearerContextInactivityNotification							ProcedureCode ::= 13
id-dLDataNotification											ProcedureCode ::= 14
id-dataUsageReport												ProcedureCode ::= 15
id-gNB-CU-UP-CounterCheck										ProcedureCode ::= 16
id-gNB-CU-UP-StatusIndication									ProcedureCode ::= 17
id-uLDataNotification											ProcedureCode ::= 18
id-mRDC-DataUsageReport											ProcedureCode ::= 19
id-TraceStart													ProcedureCode ::= 20
id-DeactivateTrace												ProcedureCode ::= 21
id-resourceStatusReportingInitiation							ProcedureCode ::= 22
id-resourceStatusReporting										ProcedureCode ::= 23
id-iAB-UPTNLAddressUpdate										ProcedureCode ::= 24
id-CellTrafficTrace												ProcedureCode ::= 25
id-earlyForwardingSNTransfer									ProcedureCode ::= 26
id-gNB-CU-CPMeasurementResultsInformation						ProcedureCode ::= 27
id-iABPSKNotification											ProcedureCode ::= 28
id-BCBearerContextSetup											ProcedureCode ::= 29
id-BCBearerContextModification									ProcedureCode ::= 30
id-BCBearerContextModificationRequired							ProcedureCode ::= 31
id-BCBearerContextRelease										ProcedureCode ::= 32
id-BCBearerContextReleaseRequest								ProcedureCode ::= 33
id-MCBearerContextSetup											ProcedureCode ::= 34
id-MCBearerContextModification									ProcedureCode ::= 35
id-MCBearerContextModificationRequired							ProcedureCode ::= 36
id-MCBearerContextRelease										ProcedureCode ::= 37
id-MCBearerContextReleaseRequest								ProcedureCode ::= 38
id-MCBearerNotification											ProcedureCode ::= 39
id-dataCollectionReportingInitiation							ProcedureCode ::= 40
id-dataCollectionReporting										ProcedureCode ::= 41



-- **************************************************************
--
-- Lists
--
-- **************************************************************

maxnoofErrors								INTEGER ::= 256
maxnoofSPLMNs								INTEGER ::= 12
maxnoofSliceItems							INTEGER ::= 1024
maxnoofIndividualE1ConnectionsToReset		INTEGER ::= 65536
maxnoofEUTRANQOSParameters					INTEGER ::= 256
maxnoofNGRANQOSParameters					INTEGER ::= 256
maxnoofDRBs									INTEGER	::= 32
maxnoofNRCGI								INTEGER	::= 512
maxnoofPDUSessionResource					INTEGER	::= 256
maxnoofQoSFlows								INTEGER	::= 64
maxnoofUPParameters							INTEGER	::= 8
maxnoofCellGroups							INTEGER	::= 4
maxnooftimeperiods							INTEGER	::= 2
maxnoofTNLAssociations						INTEGER ::= 32
maxnoofTLAs									INTEGER ::= 16
maxnoofGTPTLAs								INTEGER ::= 16
maxnoofTNLAddresses							INTEGER ::= 8
maxnoofMDTPLMNs								INTEGER ::= 16
maxnoofQoSParaSets							INTEGER ::= 8
maxnoofExtSliceItems						INTEGER ::= 65535
maxnoofDataForwardingTunneltoE-UTRAN		INTEGER ::= 256
maxnoofExtNRCGI 							INTEGER	::= 16384
maxnoofPSKs									INTEGER	::= 256
maxnoofECGI 								INTEGER	::= 512
maxnoofSMBRValues							INTEGER	::= 8
maxnoofMBSAreaSessionIDs					INTEGER ::= 256
maxnoofSharedNG-UTerminations				INTEGER ::= 8
maxnoofMRBs									INTEGER ::= 32
maxnoofMBSSessionIDs						INTEGER ::= 512
maxnoofCellsforMBS							INTEGER ::= 512
maxnoofTAIforMBS							INTEGER ::= 512
maxnoofMBSServiceAreaInformation			INTEGER ::= 256
maxnoofDUs									INTEGER ::= 512
maxnoofUEReports							INTEGER ::= 16
maxnoofThresholds							INTEGER ::= 8
maxFailedMeasPerNode						INTEGER ::= 124



-- **************************************************************
--
-- IEs
--
-- **************************************************************

id-Cause														ProtocolIE-ID ::= 0
id-CriticalityDiagnostics										ProtocolIE-ID ::= 1
id-gNB-CU-CP-UE-E1AP-ID 										ProtocolIE-ID ::= 2
id-gNB-CU-UP-UE-E1AP-ID											ProtocolIE-ID ::= 3
id-ResetType													ProtocolIE-ID ::= 4
id-UE-associatedLogicalE1-ConnectionItem						ProtocolIE-ID ::= 5
id-UE-associatedLogicalE1-ConnectionListResAck					ProtocolIE-ID ::= 6
id-gNB-CU-UP-ID													ProtocolIE-ID ::= 7
id-gNB-CU-UP-Name												ProtocolIE-ID ::= 8
id-gNB-CU-CP-Name												ProtocolIE-ID ::= 9
id-CNSupport													ProtocolIE-ID ::= 10
id-SupportedPLMNs												ProtocolIE-ID ::= 11
id-TimeToWait													ProtocolIE-ID ::= 12
id-SecurityInformation											ProtocolIE-ID ::= 13
id-UEDLAggregateMaximumBitRate									ProtocolIE-ID ::= 14
id-System-BearerContextSetupRequest								ProtocolIE-ID ::= 15
id-System-BearerContextSetupResponse							ProtocolIE-ID ::= 16
id-BearerContextStatusChange									ProtocolIE-ID ::= 17
id-System-BearerContextModificationRequest						ProtocolIE-ID ::= 18
id-System-BearerContextModificationResponse						ProtocolIE-ID ::= 19
id-System-BearerContextModificationConfirm						ProtocolIE-ID ::= 20
id-System-BearerContextModificationRequired						ProtocolIE-ID ::= 21
id-DRB-Status-List												ProtocolIE-ID ::= 22
id-ActivityNotificationLevel									ProtocolIE-ID ::= 23
id-ActivityInformation											ProtocolIE-ID ::= 24
id-Data-Usage-Report-List										ProtocolIE-ID ::= 25
id-New-UL-TNL-Information-Required								ProtocolIE-ID ::= 26
id-GNB-CU-CP-TNLA-To-Add-List									ProtocolIE-ID ::= 27
id-GNB-CU-CP-TNLA-To-Remove-List								ProtocolIE-ID ::= 28
id-GNB-CU-CP-TNLA-To-Update-List								ProtocolIE-ID ::= 29
id-GNB-CU-CP-TNLA-Setup-List									ProtocolIE-ID ::= 30
id-GNB-CU-CP-TNLA-Failed-To-Setup-List							ProtocolIE-ID ::= 31
id-DRB-To-Setup-List-EUTRAN										ProtocolIE-ID ::= 32
id-DRB-To-Modify-List-EUTRAN									ProtocolIE-ID ::= 33
id-DRB-To-Remove-List-EUTRAN									ProtocolIE-ID ::= 34
id-DRB-Required-To-Modify-List-EUTRAN							ProtocolIE-ID ::= 35
id-DRB-Required-To-Remove-List-EUTRAN							ProtocolIE-ID ::= 36
id-DRB-Setup-List-EUTRAN										ProtocolIE-ID ::= 37
id-DRB-Failed-List-EUTRAN										ProtocolIE-ID ::= 38
id-DRB-Modified-List-EUTRAN										ProtocolIE-ID ::= 39
id-DRB-Failed-To-Modify-List-EUTRAN								ProtocolIE-ID ::= 40
id-DRB-Confirm-Modified-List-EUTRAN								ProtocolIE-ID ::= 41
id-PDU-Session-Resource-To-Setup-List							ProtocolIE-ID ::= 42
id-PDU-Session-Resource-To-Modify-List							ProtocolIE-ID ::= 43
id-PDU-Session-Resource-To-Remove-List							ProtocolIE-ID ::= 44
id-PDU-Session-Resource-Required-To-Modify-List					ProtocolIE-ID ::= 45
id-PDU-Session-Resource-Setup-List								ProtocolIE-ID ::= 46
id-PDU-Session-Resource-Failed-List								ProtocolIE-ID ::= 47
id-PDU-Session-Resource-Modified-List							ProtocolIE-ID ::= 48
id-PDU-Session-Resource-Failed-To-Modify-List					ProtocolIE-ID ::= 49
id-PDU-Session-Resource-Confirm-Modified-List					ProtocolIE-ID ::= 50
id-DRB-To-Setup-Mod-List-EUTRAN									ProtocolIE-ID ::= 51
id-DRB-Setup-Mod-List-EUTRAN									ProtocolIE-ID ::= 52
id-DRB-Failed-Mod-List-EUTRAN									ProtocolIE-ID ::= 53
id-PDU-Session-Resource-Setup-Mod-List							ProtocolIE-ID ::= 54
id-PDU-Session-Resource-Failed-Mod-List							ProtocolIE-ID ::= 55
id-PDU-Session-Resource-To-Setup-Mod-List						ProtocolIE-ID ::= 56
id-TransactionID												ProtocolIE-ID ::= 57
id-Serving-PLMN													ProtocolIE-ID ::= 58
id-UE-Inactivity-Timer											ProtocolIE-ID ::= 59
id-System-GNB-CU-UP-CounterCheckRequest							ProtocolIE-ID ::= 60
id-DRBs-Subject-To-Counter-Check-List-EUTRAN					ProtocolIE-ID ::= 61
id-DRBs-Subject-To-Counter-Check-List-NG-RAN					ProtocolIE-ID ::= 62
id-PPI															ProtocolIE-ID ::= 63
id-gNB-CU-UP-Capacity											ProtocolIE-ID ::= 64
id-GNB-CU-UP-OverloadInformation								ProtocolIE-ID ::= 65
id-UEDLMaximumIntegrityProtectedDataRate						ProtocolIE-ID ::= 66
id-PDU-Session-To-Notify-List									ProtocolIE-ID ::= 67
id-PDU-Session-Resource-Data-Usage-List							ProtocolIE-ID ::= 68
id-SNSSAI														ProtocolIE-ID ::= 69
id-DataDiscardRequired											ProtocolIE-ID ::= 70
id-OldQoSFlowMap-ULendmarkerexpected							ProtocolIE-ID ::= 71
id-DRB-QoS														ProtocolIE-ID ::= 72
id-GNB-CU-UP-TNLA-To-Remove-List								ProtocolIE-ID ::= 73
id-endpoint-IP-Address-and-Port									ProtocolIE-ID ::= 74
id-TNLAssociationTransportLayerAddressgNBCUUP					ProtocolIE-ID ::= 75
id-RANUEID														ProtocolIE-ID ::= 76
id-GNB-DU-ID													ProtocolIE-ID ::= 77
id-CommonNetworkInstance										ProtocolIE-ID ::= 78
id-NetworkInstance												ProtocolIE-ID ::= 79
id-QoSFlowMappingIndication										ProtocolIE-ID ::= 80
id-TraceActivation												ProtocolIE-ID ::= 81
id-TraceID														ProtocolIE-ID ::= 82
id-SubscriberProfileIDforRFP									ProtocolIE-ID ::= 83
id-AdditionalRRMPriorityIndex									ProtocolIE-ID ::= 84
id-RetainabilityMeasurementsInfo								ProtocolIE-ID ::= 85
id-Transport-Layer-Address-Info									ProtocolIE-ID ::= 86
id-QoSMonitoringRequest											ProtocolIE-ID ::= 87
id-PDCP-StatusReportIndication									ProtocolIE-ID ::= 88
id-gNB-CU-CP-Measurement-ID										ProtocolIE-ID ::= 89
id-gNB-CU-UP-Measurement-ID										ProtocolIE-ID ::= 90
id-RegistrationRequest											ProtocolIE-ID ::= 91
id-ReportCharacteristics										ProtocolIE-ID ::= 92
id-ReportingPeriodicity											ProtocolIE-ID ::= 93
id-TNL-AvailableCapacityIndicator								ProtocolIE-ID ::= 94
id-HW-CapacityIndicator											ProtocolIE-ID ::= 95
id-RedundantCommonNetworkInstance								ProtocolIE-ID ::= 96
id-redundant-nG-UL-UP-TNL-Information							ProtocolIE-ID ::= 97
id-redundant-nG-DL-UP-TNL-Information							ProtocolIE-ID ::= 98
id-RedundantQosFlowIndicator									ProtocolIE-ID ::= 99
id-TSCTrafficCharacteristics									ProtocolIE-ID ::= 100
id-CNPacketDelayBudgetDownlink									ProtocolIE-ID ::= 101
id-CNPacketDelayBudgetUplink									ProtocolIE-ID ::= 102
id-ExtendedPacketDelayBudget									ProtocolIE-ID ::= 103
id-AdditionalPDCPduplicationInformation							ProtocolIE-ID ::= 104
id-RedundantPDUSessionInformation								ProtocolIE-ID ::= 105
id-RedundantPDUSessionInformation-used							ProtocolIE-ID ::= 106
id-QoS-Mapping-Information										ProtocolIE-ID ::= 107
id-DLUPTNLAddressToUpdateList									ProtocolIE-ID ::= 108
id-ULUPTNLAddressToUpdateList									ProtocolIE-ID ::= 109
id-NPNSupportInfo												ProtocolIE-ID ::= 110
id-NPNContextInfo												ProtocolIE-ID ::= 111
id-MDTConfiguration												ProtocolIE-ID ::= 112
id-ManagementBasedMDTPLMNList									ProtocolIE-ID ::= 113
id-TraceCollectionEntityIPAddress								ProtocolIE-ID ::= 114
id-PrivacyIndicator												ProtocolIE-ID ::= 115
id-TraceCollectionEntityURI										ProtocolIE-ID ::= 116
id-URIaddress													ProtocolIE-ID ::= 117
id-EHC-Parameters												ProtocolIE-ID ::= 118
id-DRBs-Subject-To-Early-Forwarding-List						ProtocolIE-ID ::= 119
id-DAPSRequestInfo												ProtocolIE-ID ::= 120
id-CHOInitiation												ProtocolIE-ID ::= 121
id-EarlyForwardingCOUNTReq										ProtocolIE-ID ::= 122
id-EarlyForwardingCOUNTInfo										ProtocolIE-ID ::= 123
id-AlternativeQoSParaSetList									ProtocolIE-ID ::= 124
id-ExtendedSliceSupportList										ProtocolIE-ID ::= 125
id-MCG-OfferedGBRQoSFlowInfo									ProtocolIE-ID ::= 126
id-Number-of-tunnels											ProtocolIE-ID ::= 127
id-DRB-Measurement-Results-Information-List						ProtocolIE-ID ::= 128
id-Extended-GNB-CU-CP-Name										ProtocolIE-ID ::= 129
id-Extended-GNB-CU-UP-Name										ProtocolIE-ID ::= 130
id-DataForwardingtoE-UTRANInformationList						ProtocolIE-ID ::= 131
id-QosMonitoringReportingFrequency								ProtocolIE-ID ::= 132
id-QoSMonitoringDisabled										ProtocolIE-ID ::= 133
id-AdditionalHandoverInfo										ProtocolIE-ID ::= 134
id-Extended-NR-CGI-Support-List									ProtocolIE-ID ::= 135
id-DataForwardingtoNG-RANQoSFlowInformationList					ProtocolIE-ID ::= 136
id-MaxCIDEHCDL													ProtocolIE-ID ::= 137
id-ignoreMappingRuleIndication									ProtocolIE-ID ::= 138
id-DirectForwardingPathAvailability								ProtocolIE-ID ::= 139
id-EarlyDataForwardingIndicator									ProtocolIE-ID ::= 140
id-QoSFlowsDRBRemapping											ProtocolIE-ID ::= 141
id-DataForwardingSourceIPAddress								ProtocolIE-ID ::= 142
id-SecurityIndicationModify										ProtocolIE-ID ::= 143
id-IAB-Donor-CU-UPPSKInfo										ProtocolIE-ID ::= 144
id-ECGI-Support-List											ProtocolIE-ID ::= 145
id-MDTPollutedMeasurementIndicator								ProtocolIE-ID ::= 146
id-M4ReportAmount 												ProtocolIE-ID ::= 147
id-M6ReportAmount 												ProtocolIE-ID ::= 148
id-M7ReportAmount 												ProtocolIE-ID ::= 149
id-UESliceMaximumBitRateList									ProtocolIE-ID ::= 150
id-PDUSession-PairID											ProtocolIE-ID ::= 151
id-SurvivalTime													ProtocolIE-ID ::= 152
id-UDC-Parameters												ProtocolIE-ID ::= 153
id-SCGActivationStatus											ProtocolIE-ID ::= 154
id-GNB-CU-CP-MBS-E1AP-ID										ProtocolIE-ID ::= 155
id-GNB-CU-UP-MBS-E1AP-ID										ProtocolIE-ID ::= 156
id-GlobalMBSSessionID											ProtocolIE-ID ::= 157
id-BCBearerContextToSetup										ProtocolIE-ID ::= 158
id-BCBearerContextToSetupResponse								ProtocolIE-ID ::= 159
id-BCBearerContextToModify										ProtocolIE-ID ::= 160
id-BCBearerContextToModifyResponse								ProtocolIE-ID ::= 161
id-BCBearerContextToModifyRequired								ProtocolIE-ID ::= 162
id-BCBearerContextToModifyConfirm								ProtocolIE-ID ::= 163
id-MCBearerContextToSetup										ProtocolIE-ID ::= 164
id-MCBearerContextToSetupResponse								ProtocolIE-ID ::= 165
id-MCBearerContextToModify										ProtocolIE-ID ::= 166
id-MCBearerContextToModifyResponse								ProtocolIE-ID ::= 167
id-MCBearerContextToModifyRequired								ProtocolIE-ID ::= 168
id-MCBearerContextToModifyConfirm								ProtocolIE-ID ::= 169
id-MBSMulticastF1UContextDescriptor								ProtocolIE-ID ::= 170
id-gNB-CU-UP-MBS-Support-Info									ProtocolIE-ID ::= 171
id-SecurityIndication											ProtocolIE-ID ::= 172
id-SecurityResult												ProtocolIE-ID ::= 173
id-SDTContinueROHC												ProtocolIE-ID ::= 174
id-SDTindicatorSetup											ProtocolIE-ID ::= 175
id-SDTindicatorMod												ProtocolIE-ID ::= 176
id-DiscardTimerExtended											ProtocolIE-ID ::= 177
id-ManagementBasedMDTPLMNModificationList						ProtocolIE-ID ::= 178
id-MCForwardingResourceRequest									ProtocolIE-ID ::= 179
id-MCForwardingResourceIndication								ProtocolIE-ID ::= 180
id-MCForwardingResourceResponse									ProtocolIE-ID ::= 181
id-MCForwardingResourceRelease									ProtocolIE-ID ::= 182
id-MCForwardingResourceReleaseIndication						ProtocolIE-ID ::= 183
id-PDCP-COUNT-Reset												ProtocolIE-ID ::= 184
id-MBSSessionAssociatedInfoNonSupportToSupport					ProtocolIE-ID ::= 185
id-VersionID													ProtocolIE-ID ::= 186
id-InactivityInformationRequest									ProtocolIE-ID ::= 187
id-UEInactivityInformation										ProtocolIE-ID ::= 188
id-MBSAreaSessionID												ProtocolIE-ID ::= 189
id-Secondary-PDU-Session-Data-Forwarding-Information			ProtocolIE-ID ::= 190
id-MBSSessionResourceNotification								ProtocolIE-ID ::= 191
id-MCBearerContextInactivityTimer								ProtocolIE-ID ::= 192
id-MCBearerContextStatusChange									ProtocolIE-ID ::= 193
id-MT-SDT-Information 											ProtocolIE-ID ::= 194
id-MT-SDT-Information-Request									ProtocolIE-ID ::= 195
id-SDT-data-size-threshold										ProtocolIE-ID ::= 196
id-SDT-data-size-threshold-Crossed								ProtocolIE-ID ::= 197
id-SpecialTriggeringPurpose										ProtocolIE-ID ::= 198
id-AssociatedSessionID											ProtocolIE-ID ::= 199
id-MBS-ServiceArea												ProtocolIE-ID ::= 200
id-PDUSetQoSParameters											ProtocolIE-ID ::= 201
id-N6JitterInformation											ProtocolIE-ID ::= 202
id-ECNMarkingorCongestionInformationReportingRequest			ProtocolIE-ID ::= 203
id-ECNMarkingorCongestionInformationReportingStatus				ProtocolIE-ID ::= 204
id-PDUSetbasedHandlingIndicator 								ProtocolIE-ID ::= 205
id-IndirectPathIndication										ProtocolIE-ID ::= 206
id-F1UTunnelNotEstablished										ProtocolIE-ID ::= 207
id-F1U-TNL-InfoToAdd-List										ProtocolIE-ID ::= 208
id-F1U-TNL-InfoAdded-List										ProtocolIE-ID ::= 209
id-F1U-TNL-InfoToAddOrModify-List								ProtocolIE-ID ::= 210
id-F1U-TNL-InfoAddedOrModified-List								ProtocolIE-ID ::= 211
id-F1U-TNL-InfoToRelease-List									ProtocolIE-ID ::= 212
id-BroadcastF1U-ContextReferenceE1								ProtocolIE-ID ::= 213
id-PSIbasedDiscardTimer											ProtocolIE-ID ::= 214
id-UserPlaneErrorIndicator										ProtocolIE-ID ::= 215
id-MaximumDataBurstVolume 										ProtocolIE-ID ::= 216
id-BCBearerContextNGU-TNLInfoatNGRAN-Request					ProtocolIE-ID ::= 217
id-PDCPSNGapReport												ProtocolIE-ID ::= 218
id-UserPlaneFailureIndication									ProtocolIE-ID ::= 219
id-InactivityMonitoring											ProtocolIE-ID ::= 220
id-MCBearerContextNGUTnlInfoatNGRANReplaceRequest				ProtocolIE-ID ::= 221
id-LTMInitiation												ProtocolIE-ID ::= 222
id-RegistrationRequestForDataCollection							ProtocolIE-ID ::= 223
id-ReportCharacteristicsForDataCollection						ProtocolIE-ID ::= 224
id-ReportingPeriodicityForDataCollection						ProtocolIE-ID ::= 225
id-UEAssociatedInfoResult-List									ProtocolIE-ID ::= 226
id-DataCollectionID												ProtocolIE-ID ::= 227
id-PduSetDelayBudgetDownlink									ProtocolIE-ID ::= 228
id-PduSetDelayBudgetUplink									ProtocolIE-ID ::= 229
id-PduSetErrorRateDownlink									ProtocolIE-ID ::= 230
id-PduSetErrorRateUplink										ProtocolIE-ID ::= 231
id-MonitoringRequestonAvailableBitrate						ProtocolIE-ID ::= 232
id-MMSID														ProtocolIE-ID ::= 233
id-Remaining-time-based-rLC-retransmission-threshold			ProtocolIE-ID ::= 234
id-Remaining-time-based-rLC-polling-threshold					ProtocolIE-ID ::= 235
id-DL-PDU-Set-Info-Marking-Support-Ind						ProtocolIE-ID ::= 236
id-UEPerformanceCollectionConfiguration							ProtocolIE-ID ::= 237
id-NodeMeasurementInitiationResult-List							ProtocolIE-ID ::= 238


END

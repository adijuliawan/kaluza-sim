-- Extracted by spec/tools/docx_asn1.py 1.0 from 3GPP TS 38.413 j40 (38413-j40.zip, sha256 7e559e1cfdcea8459e0b0c9e58f91b603c5f60ebebbda949b4d06acf4fcc5a4f).
-- Do not edit: regenerate with spec/tools/docx_asn1.py. Text (c) 3GPP; see spec/INDEX.tsv for the source.

NGAP-Constants {
itu-t (0) identified-organization (4) etsi (0) mobileDomain (0)
ngran-Access (22) modules (3) ngap (1) version1 (1) ngap-Constants (4) }

DEFINITIONS AUTOMATIC TAGS ::=

BEGIN

-- **************************************************************
--
-- IE parameter types from other modules.
--
-- **************************************************************

IMPORTS

	ProcedureCode,
	ProtocolIE-ID
FROM NGAP-CommonDataTypes;


-- **************************************************************
--
-- Elementary Procedures
--
-- **************************************************************

id-AMFConfigurationUpdate					ProcedureCode ::= 0
id-AMFStatusIndication						ProcedureCode ::= 1
id-CellTrafficTrace							ProcedureCode ::= 2
id-DeactivateTrace							ProcedureCode ::= 3
id-DownlinkNASTransport						ProcedureCode ::= 4
id-DownlinkNonUEAssociatedNRPPaTransport	ProcedureCode ::= 5
id-DownlinkRANConfigurationTransfer			ProcedureCode ::= 6
id-DownlinkRANStatusTransfer				ProcedureCode ::= 7
id-DownlinkUEAssociatedNRPPaTransport		ProcedureCode ::= 8
id-ErrorIndication							ProcedureCode ::= 9
id-HandoverCancel							ProcedureCode ::= 10
id-HandoverNotification						ProcedureCode ::= 11
id-HandoverPreparation						ProcedureCode ::= 12
id-HandoverResourceAllocation				ProcedureCode ::= 13
id-InitialContextSetup						ProcedureCode ::= 14
id-InitialUEMessage							ProcedureCode ::= 15
id-LocationReportingControl					ProcedureCode ::= 16
id-LocationReportingFailureIndication		ProcedureCode ::= 17
id-LocationReport							ProcedureCode ::= 18
id-NASNonDeliveryIndication					ProcedureCode ::= 19
id-NGReset									ProcedureCode ::= 20
id-NGSetup									ProcedureCode ::= 21
id-OverloadStart							ProcedureCode ::= 22
id-OverloadStop								ProcedureCode ::= 23
id-Paging									ProcedureCode ::= 24
id-PathSwitchRequest						ProcedureCode ::= 25
id-PDUSessionResourceModify					ProcedureCode ::= 26
id-PDUSessionResourceModifyIndication		ProcedureCode ::= 27
id-PDUSessionResourceRelease				ProcedureCode ::= 28
id-PDUSessionResourceSetup					ProcedureCode ::= 29
id-PDUSessionResourceNotify					ProcedureCode ::= 30
id-PrivateMessage							ProcedureCode ::= 31
id-PWSCancel								ProcedureCode ::= 32
id-PWSFailureIndication						ProcedureCode ::= 33
id-PWSRestartIndication						ProcedureCode ::= 34
id-RANConfigurationUpdate					ProcedureCode ::= 35
id-RerouteNASRequest						ProcedureCode ::= 36
id-RRCInactiveTransitionReport				ProcedureCode ::= 37
id-TraceFailureIndication					ProcedureCode ::= 38
id-TraceStart								ProcedureCode ::= 39
id-UEContextModification					ProcedureCode ::= 40
id-UEContextRelease							ProcedureCode ::= 41
id-UEContextReleaseRequest					ProcedureCode ::= 42
id-UERadioCapabilityCheck					ProcedureCode ::= 43
id-UERadioCapabilityInfoIndication			ProcedureCode ::= 44
id-UETNLABindingRelease						ProcedureCode ::= 45
id-UplinkNASTransport						ProcedureCode ::= 46
id-UplinkNonUEAssociatedNRPPaTransport		ProcedureCode ::= 47
id-UplinkRANConfigurationTransfer			ProcedureCode ::= 48
id-UplinkRANStatusTransfer					ProcedureCode ::= 49
id-UplinkUEAssociatedNRPPaTransport			ProcedureCode ::= 50
id-WriteReplaceWarning						ProcedureCode ::= 51
id-SecondaryRATDataUsageReport				ProcedureCode ::= 52
id-UplinkRIMInformationTransfer				ProcedureCode ::= 53
id-DownlinkRIMInformationTransfer			ProcedureCode ::= 54
id-RetrieveUEInformation					ProcedureCode ::= 55
id-UEInformationTransfer					ProcedureCode ::= 56
id-RANCPRelocationIndication				ProcedureCode ::= 57
id-UEContextResume							ProcedureCode ::= 58
id-UEContextSuspend							ProcedureCode ::= 59
id-UERadioCapabilityIDMapping				ProcedureCode ::= 60
id-HandoverSuccess							ProcedureCode ::= 61
id-UplinkRANEarlyStatusTransfer				ProcedureCode ::= 62
id-DownlinkRANEarlyStatusTransfer			ProcedureCode ::= 63
id-AMFCPRelocationIndication				ProcedureCode ::= 64
id-ConnectionEstablishmentIndication		ProcedureCode ::= 65
id-BroadcastSessionModification				ProcedureCode ::= 66
id-BroadcastSessionRelease					ProcedureCode ::= 67
id-BroadcastSessionSetup					ProcedureCode ::= 68
id-DistributionSetup 						ProcedureCode ::= 69
id-DistributionRelease 						ProcedureCode ::= 70
id-MulticastSessionActivation 				ProcedureCode ::= 71
id-MulticastSessionDeactivation 			ProcedureCode ::= 72
id-MulticastSessionUpdate 					ProcedureCode ::= 73
id-MulticastGroupPaging						ProcedureCode ::= 74
id-BroadcastSessionReleaseRequired			ProcedureCode ::= 75
id-TimingSynchronisationStatus				ProcedureCode ::= 76
id-TimingSynchronisationStatusReport		ProcedureCode ::= 77
id-MTCommunicationHandling					ProcedureCode ::= 78
id-RANPagingRequest							ProcedureCode ::= 79
id-BroadcastSessionTransport				ProcedureCode ::= 80
id-NGRemoval								ProcedureCode ::= 81
id-InventoryRequest							ProcedureCode ::= 82
id-InventoryReport							ProcedureCode ::= 83
id-CommandRequest							ProcedureCode ::= 84
id-AIOTSessionRelease						ProcedureCode ::= 85
id-AIOTSessionReleaseRequest				ProcedureCode ::= 86



-- **************************************************************
--
-- Extension constants
--
-- **************************************************************

maxPrivateIEs							INTEGER ::= 65535
maxProtocolExtensions					INTEGER ::= 65535
maxProtocolIEs							INTEGER ::= 65535

-- **************************************************************
--
-- Lists
--
-- **************************************************************

	maxnoofAllowedAreas							INTEGER ::= 16
	maxnoofAllowedCAGsperPLMN					INTEGER ::= 256
	maxnoofAllowedS-NSSAIs						INTEGER ::= 8
	maxnoofBluetoothName						INTEGER ::= 4
	maxnoofBPLMNs								INTEGER ::= 12
	maxnoofCAGSperCell							INTEGER ::= 64
	maxnoofCellIDforMDT							INTEGER ::= 32
	maxnoofCellIDforWarning						INTEGER ::= 65535
	maxnoofCellinAoI							INTEGER ::= 256
	maxnoofCellinEAI							INTEGER ::= 65535
	maxnoofCellinTAI							INTEGER ::= 65535
	maxnoofCellsforMBS							INTEGER ::= 8192
	maxnoofCellsingNB							INTEGER ::= 16384
	maxnoofCellsinngeNB							INTEGER ::= 256
	maxnoofCellsinNGRANNode						INTEGER ::= 16384
	maxnoofCellsinUEHistoryInfo					INTEGER ::= 16
	maxnoofCellsUEMovingTrajectory				INTEGER ::= 16
	maxnoofDRBs									INTEGER ::= 32
	maxnoofEmergencyAreaID						INTEGER ::= 65535
	maxnoofEAIforRestart						INTEGER ::= 256
	maxnoofEPLMNs								INTEGER ::= 15
	maxnoofEPLMNsPlusOne						INTEGER ::= 16
	maxnoofE-RABs								INTEGER ::= 256
	maxnoofErrors								INTEGER ::= 256
	maxnoofExtSliceItems						INTEGER ::= 65535
	maxnoofForbTACs								INTEGER ::= 4096
	maxnoofFreqforMDT							INTEGER ::= 8
	maxnoofGUAMIs								INTEGER ::= 1024
	maxnoofMBSAreaSessionIDs					INTEGER ::= 256
	maxnoofMBSFSAs								INTEGER ::= 64
	maxnoofMBSQoSFlows							INTEGER ::= 64
	maxnoofMBSSessions							INTEGER ::= 32
	maxnoofMBSSessionsofUE						INTEGER ::= 256
	maxnoofMBSServiceAreaInformation			INTEGER ::= 256
	maxnoofMDTPLMNs								INTEGER ::= 16
	maxnoofMRBs									INTEGER ::= 32
	maxnoofMultiConnectivity					INTEGER ::= 4
	maxnoofMultiConnectivityMinusOne			INTEGER ::= 3
	maxnoofNeighPCIforMDT						INTEGER ::= 32
	maxnoofNGAPIESupportInfo					INTEGER ::= 32
	maxnoofNGConnectionsToReset					INTEGER ::= 65536
	maxnoofNRCellBands							INTEGER ::= 32
	maxnoofNSAGs								INTEGER ::= 256
	maxnoofPagingAreas							INTEGER ::= 64
	maxnoofPC5QoSFlows 							INTEGER ::= 2048
	maxnoofPDUSessions							INTEGER ::= 256
	maxnoofPLMNs								INTEGER ::= 12
	maxnoofPSCellsPerPrimaryCellinUEHistoryInfo	INTEGER ::= 8
	maxnoofQosFlows								INTEGER ::= 64
	maxnoofQosParaSets							INTEGER ::= 8
	maxnoofRANNodeinAoI							INTEGER ::= 64
	maxnoofRecommendedCells						INTEGER ::= 16
	maxnoofRecommendedRANNodes					INTEGER ::= 16
	maxnoofAoI									INTEGER ::= 64
	maxnoofAoIMinusOne							INTEGER ::= 63
	maxnoofFlightInfoReportControl				INTEGER ::= 64
	maxnoofReportedCells						INTEGER ::= 256
	maxnoofSensorName							INTEGER ::= 3
	maxnoofServedGUAMIs							INTEGER ::= 256
	maxnoofSliceItems							INTEGER ::= 1024
	maxnoofSuccessfulHOReports					INTEGER ::= 64
	maxnoofTACs									INTEGER ::= 256
	maxnoofTACsinNTN							INTEGER ::= 12
	maxnoofTAforMDT								INTEGER ::= 8
	maxnoofTAIforInactive						INTEGER ::= 16
	maxnoofSupportedTAIforMBS					INTEGER ::= 256
	maxnoofTAIforMBS							INTEGER ::= 1024
	maxnoofTAIforPaging							INTEGER ::= 16
	maxnoofTAIforRestart						INTEGER ::= 2048
	maxnoofTAIforWarning						INTEGER ::= 65535
	maxnoofTAIinAoI								INTEGER ::= 16
	maxnoofTimePeriods							INTEGER ::= 2
	maxnoofTNLAssociations						INTEGER ::= 32
	maxnoofUEsforPaging							INTEGER ::=	4096
	maxnoofUETypes								INTEGER ::=	8
	maxnoofWLANName								INTEGER ::= 4
	maxnoofXnExtTLAs							INTEGER ::= 16
	maxnoofXnGTP-TLAs							INTEGER ::= 16
	maxnoofXnTLAs								INTEGER ::= 2
	maxnoofCandidateCells						INTEGER ::= 32
	maxnoofTargetS-NSSAIs						INTEGER ::= 8
	maxNRARFCN									INTEGER ::= 3279165
	maxnoofCellIDforQMC							INTEGER ::= 32
	maxnoofPLMNforQMC							INTEGER ::= 16
	maxnoofUEAppLayerMeas						INTEGER ::= 16
	maxnoofSNSSAIforQMC							INTEGER ::= 16
	maxnoofTAforQMC								INTEGER ::= 8
	maxnoofThresholdsForExcessPacketDelay		INTEGER ::= 255
	maxnoofESNPNs								INTEGER ::= 15
	maxnoofCandidateRelayUEs					INTEGER ::= 32
	maxnoofSuccessfulPSCellChangeReports       	INTEGER ::= 64
	maxnoofCellsTSS								INTEGER ::= 16384
	maxnoofPeriodicities						INTEGER ::= 8
	maxnoofCAGforMDT							INTEGER ::= 256
	maxnoofMDTSNPNs								INTEGER ::= 16
	maxnoofPartiallyAllowedS-NSSAIs				INTEGER ::= 8
	maxnoofRSPPQoSFlows							INTEGER ::= 2048
	maxnoofSliceItemsforMDT						INTEGER ::= 1024
	maxnoofAreaNTN								INTEGER ::= 8
	maxnoofIntendedAreasforMBS					INTEGER ::= 65536
	maxnoofRequestedSNSSAIs						INTEGER ::= 8
	maxnoofReaders								INTEGER ::= 65535
	maxnoofDevices								INTEGER ::= 65535
	maxnoofAIoTAreas							INTEGER ::= 256
	maxnoofThresholds							INTEGER ::= 8



-- **************************************************************
--
-- IEs
--
-- **************************************************************

	id-AllowedNSSAI											ProtocolIE-ID ::= 0
	id-AMFName												ProtocolIE-ID ::= 1
	id-AMFOverloadResponse									ProtocolIE-ID ::= 2
	id-AMFSetID												ProtocolIE-ID ::= 3
	id-AMF-TNLAssociationFailedToSetupList					ProtocolIE-ID ::= 4
	id-AMF-TNLAssociationSetupList							ProtocolIE-ID ::= 5
	id-AMF-TNLAssociationToAddList							ProtocolIE-ID ::= 6
	id-AMF-TNLAssociationToRemoveList						ProtocolIE-ID ::= 7
	id-AMF-TNLAssociationToUpdateList						ProtocolIE-ID ::= 8
	id-AMFTrafficLoadReductionIndication					ProtocolIE-ID ::= 9
	id-AMF-UE-NGAP-ID										ProtocolIE-ID ::= 10
	id-AssistanceDataForPaging								ProtocolIE-ID ::= 11
	id-BroadcastCancelledAreaList							ProtocolIE-ID ::= 12
	id-BroadcastCompletedAreaList							ProtocolIE-ID ::= 13
	id-CancelAllWarningMessages								ProtocolIE-ID ::= 14
	id-Cause												ProtocolIE-ID ::= 15
	id-CellIDListForRestart									ProtocolIE-ID ::= 16
	id-ConcurrentWarningMessageInd							ProtocolIE-ID ::= 17
	id-CoreNetworkAssistanceInformationForInactive			ProtocolIE-ID ::= 18
	id-CriticalityDiagnostics								ProtocolIE-ID ::= 19
	id-DataCodingScheme										ProtocolIE-ID ::= 20
	id-DefaultPagingDRX										ProtocolIE-ID ::= 21
	id-DirectForwardingPathAvailability						ProtocolIE-ID ::= 22
	id-EmergencyAreaIDListForRestart						ProtocolIE-ID ::= 23
	id-EmergencyFallbackIndicator							ProtocolIE-ID ::= 24
	id-EUTRA-CGI											ProtocolIE-ID ::= 25
	id-FiveG-S-TMSI											ProtocolIE-ID ::= 26
	id-GlobalRANNodeID										ProtocolIE-ID ::= 27
	id-GUAMI												ProtocolIE-ID ::= 28
	id-HandoverType											ProtocolIE-ID ::= 29
	id-IMSVoiceSupportIndicator								ProtocolIE-ID ::= 30
	id-IndexToRFSP											ProtocolIE-ID ::= 31
	id-InfoOnRecommendedCellsAndRANNodesForPaging			ProtocolIE-ID ::= 32
	id-LocationReportingRequestType							ProtocolIE-ID ::= 33
	id-MaskedIMEISV											ProtocolIE-ID ::= 34
	id-MessageIdentifier									ProtocolIE-ID ::= 35
	id-MobilityRestrictionList								ProtocolIE-ID ::= 36
	id-NASC													ProtocolIE-ID ::= 37
	id-NAS-PDU												ProtocolIE-ID ::= 38
	id-NASSecurityParametersFromNGRAN						ProtocolIE-ID ::= 39
	id-NewAMF-UE-NGAP-ID									ProtocolIE-ID ::= 40
	id-NewSecurityContextInd								ProtocolIE-ID ::= 41
	id-NGAP-Message											ProtocolIE-ID ::= 42
	id-NGRAN-CGI											ProtocolIE-ID ::= 43
	id-NGRANTraceID											ProtocolIE-ID ::= 44
	id-NR-CGI												ProtocolIE-ID ::= 45
	id-NRPPa-PDU											ProtocolIE-ID ::= 46
	id-NumberOfBroadcastsRequested							ProtocolIE-ID ::= 47
	id-OldAMF												ProtocolIE-ID ::= 48
	id-OverloadStartNSSAIList								ProtocolIE-ID ::= 49
	id-PagingDRX											ProtocolIE-ID ::= 50
	id-PagingOrigin											ProtocolIE-ID ::= 51
	id-PagingPriority										ProtocolIE-ID ::= 52
	id-PDUSessionResourceAdmittedList						ProtocolIE-ID ::= 53
	id-PDUSessionResourceFailedToModifyListModRes			ProtocolIE-ID ::= 54
	id-PDUSessionResourceFailedToSetupListCxtRes			ProtocolIE-ID ::= 55
	id-PDUSessionResourceFailedToSetupListHOAck				ProtocolIE-ID ::= 56
	id-PDUSessionResourceFailedToSetupListPSReq				ProtocolIE-ID ::= 57
	id-PDUSessionResourceFailedToSetupListSURes				ProtocolIE-ID ::= 58
	id-PDUSessionResourceHandoverList						ProtocolIE-ID ::= 59
	id-PDUSessionResourceListCxtRelCpl						ProtocolIE-ID ::= 60
	id-PDUSessionResourceListHORqd							ProtocolIE-ID ::= 61
	id-PDUSessionResourceModifyListModCfm					ProtocolIE-ID ::= 62
	id-PDUSessionResourceModifyListModInd					ProtocolIE-ID ::= 63
	id-PDUSessionResourceModifyListModReq					ProtocolIE-ID ::= 64
	id-PDUSessionResourceModifyListModRes					ProtocolIE-ID ::= 65
	id-PDUSessionResourceNotifyList							ProtocolIE-ID ::= 66
	id-PDUSessionResourceReleasedListNot					ProtocolIE-ID ::= 67
	id-PDUSessionResourceReleasedListPSAck					ProtocolIE-ID ::= 68
	id-PDUSessionResourceReleasedListPSFail					ProtocolIE-ID ::= 69
	id-PDUSessionResourceReleasedListRelRes					ProtocolIE-ID ::= 70
	id-PDUSessionResourceSetupListCxtReq					ProtocolIE-ID ::= 71
	id-PDUSessionResourceSetupListCxtRes					ProtocolIE-ID ::= 72
	id-PDUSessionResourceSetupListHOReq						ProtocolIE-ID ::= 73
	id-PDUSessionResourceSetupListSUReq						ProtocolIE-ID ::= 74
	id-PDUSessionResourceSetupListSURes						ProtocolIE-ID ::= 75
	id-PDUSessionResourceToBeSwitchedDLList					ProtocolIE-ID ::= 76
	id-PDUSessionResourceSwitchedList						ProtocolIE-ID ::= 77
	id-PDUSessionResourceToReleaseListHOCmd					ProtocolIE-ID ::= 78
	id-PDUSessionResourceToReleaseListRelCmd				ProtocolIE-ID ::= 79
	id-PLMNSupportList										ProtocolIE-ID ::= 80
	id-PWSFailedCellIDList									ProtocolIE-ID ::= 81
	id-RANNodeName											ProtocolIE-ID ::= 82
	id-RANPagingPriority									ProtocolIE-ID ::= 83
	id-RANStatusTransfer-TransparentContainer				ProtocolIE-ID ::= 84
	id-RAN-UE-NGAP-ID										ProtocolIE-ID ::= 85
	id-RelativeAMFCapacity									ProtocolIE-ID ::= 86
	id-RepetitionPeriod										ProtocolIE-ID ::= 87
	id-ResetType											ProtocolIE-ID ::= 88
	id-RoutingID											ProtocolIE-ID ::= 89
	id-RRCEstablishmentCause								ProtocolIE-ID ::= 90
	id-RRCInactiveTransitionReportRequest					ProtocolIE-ID ::= 91
	id-RRCState												ProtocolIE-ID ::= 92
	id-SecurityContext										ProtocolIE-ID ::= 93
	id-SecurityKey											ProtocolIE-ID ::= 94
	id-SerialNumber											ProtocolIE-ID ::= 95
	id-ServedGUAMIList										ProtocolIE-ID ::= 96
	id-SliceSupportList										ProtocolIE-ID ::= 97
	id-SONConfigurationTransferDL							ProtocolIE-ID ::= 98
	id-SONConfigurationTransferUL							ProtocolIE-ID ::= 99
	id-SourceAMF-UE-NGAP-ID									ProtocolIE-ID ::= 100
	id-SourceToTarget-TransparentContainer					ProtocolIE-ID ::= 101
	id-SupportedTAList										ProtocolIE-ID ::= 102
	id-TAIListForPaging										ProtocolIE-ID ::= 103
	id-TAIListForRestart									ProtocolIE-ID ::= 104
	id-TargetID												ProtocolIE-ID ::= 105
	id-TargetToSource-TransparentContainer					ProtocolIE-ID ::= 106
	id-TimeToWait											ProtocolIE-ID ::= 107
	id-TraceActivation										ProtocolIE-ID ::= 108
	id-TraceCollectionEntityIPAddress						ProtocolIE-ID ::= 109
	id-UEAggregateMaximumBitRate							ProtocolIE-ID ::= 110
	id-UE-associatedLogicalNG-connectionList				ProtocolIE-ID ::= 111
	id-UEContextRequest										ProtocolIE-ID ::= 112
	id-UE-NGAP-IDs											ProtocolIE-ID ::= 114
	id-UEPagingIdentity										ProtocolIE-ID ::= 115
	id-UEPresenceInAreaOfInterestList						ProtocolIE-ID ::= 116
	id-UERadioCapability									ProtocolIE-ID ::= 117
	id-UERadioCapabilityForPaging							ProtocolIE-ID ::= 118
	id-UESecurityCapabilities								ProtocolIE-ID ::= 119
	id-UnavailableGUAMIList									ProtocolIE-ID ::= 120
	id-UserLocationInformation								ProtocolIE-ID ::= 121
	id-WarningAreaList										ProtocolIE-ID ::= 122
	id-WarningMessageContents								ProtocolIE-ID ::= 123
	id-WarningSecurityInfo									ProtocolIE-ID ::= 124
	id-WarningType											ProtocolIE-ID ::= 125
	id-AdditionalUL-NGU-UP-TNLInformation					ProtocolIE-ID ::= 126
	id-DataForwardingNotPossible							ProtocolIE-ID ::= 127
	id-DL-NGU-UP-TNLInformation								ProtocolIE-ID ::= 128
	id-NetworkInstance										ProtocolIE-ID ::= 129
	id-PDUSessionAggregateMaximumBitRate					ProtocolIE-ID ::= 130
	id-PDUSessionResourceFailedToModifyListModCfm			ProtocolIE-ID ::= 131
	id-PDUSessionResourceFailedToSetupListCxtFail			ProtocolIE-ID ::= 132
	id-PDUSessionResourceListCxtRelReq						ProtocolIE-ID ::= 133
	id-PDUSessionType										ProtocolIE-ID ::= 134
	id-QosFlowAddOrModifyRequestList						ProtocolIE-ID ::= 135
	id-QosFlowSetupRequestList								ProtocolIE-ID ::= 136
	id-QosFlowToReleaseList									ProtocolIE-ID ::= 137
	id-SecurityIndication									ProtocolIE-ID ::= 138
	id-UL-NGU-UP-TNLInformation								ProtocolIE-ID ::= 139
	id-UL-NGU-UP-TNLModifyList								ProtocolIE-ID ::= 140
	id-WarningAreaCoordinates								ProtocolIE-ID ::= 141
	id-PDUSessionResourceSecondaryRATUsageList				ProtocolIE-ID ::= 142
	id-HandoverFlag											ProtocolIE-ID ::= 143
	id-SecondaryRATUsageInformation							ProtocolIE-ID ::= 144
	id-PDUSessionResourceReleaseResponseTransfer			ProtocolIE-ID ::= 145
	id-RedirectionVoiceFallback								ProtocolIE-ID ::= 146
	id-UERetentionInformation								ProtocolIE-ID ::= 147
	id-S-NSSAI												ProtocolIE-ID ::= 148
	id-PSCellInformation									ProtocolIE-ID ::= 149
	id-LastEUTRAN-PLMNIdentity								ProtocolIE-ID ::= 150
	id-MaximumIntegrityProtectedDataRate-DL					ProtocolIE-ID ::= 151
	id-AdditionalDLForwardingUPTNLInformation				ProtocolIE-ID ::= 152
	id-AdditionalDLUPTNLInformationForHOList				ProtocolIE-ID ::= 153
	id-AdditionalNGU-UP-TNLInformation						ProtocolIE-ID ::= 154
	id-AdditionalDLQosFlowPerTNLInformation					ProtocolIE-ID ::= 155
	id-SecurityResult										ProtocolIE-ID ::= 156
	id-ENDC-SONConfigurationTransferDL						ProtocolIE-ID ::= 157
	id-ENDC-SONConfigurationTransferUL						ProtocolIE-ID ::= 158
	id-OldAssociatedQosFlowList-ULendmarkerexpected			ProtocolIE-ID ::= 159
	id-CNTypeRestrictionsForEquivalent						ProtocolIE-ID ::= 160
	id-CNTypeRestrictionsForServing							ProtocolIE-ID ::= 161
	id-NewGUAMI												ProtocolIE-ID ::= 162
	id-ULForwarding											ProtocolIE-ID ::= 163
	id-ULForwardingUP-TNLInformation						ProtocolIE-ID ::= 164
	id-CNAssistedRANTuning									ProtocolIE-ID ::= 165
	id-CommonNetworkInstance								ProtocolIE-ID ::= 166
	id-NGRAN-TNLAssociationToRemoveList						ProtocolIE-ID ::= 167
	id-TNLAssociationTransportLayerAddressNGRAN				ProtocolIE-ID ::= 168
	id-EndpointIPAddressAndPort								ProtocolIE-ID ::= 169
	id-LocationReportingAdditionalInfo						ProtocolIE-ID ::= 170
	id-SourceToTarget-AMFInformationReroute					ProtocolIE-ID ::= 171
	id-AdditionalULForwardingUPTNLInformation				ProtocolIE-ID ::= 172
	id-SCTP-TLAs											ProtocolIE-ID ::= 173
	id-SelectedPLMNIdentity									ProtocolIE-ID ::= 174
	id-RIMInformationTransfer								ProtocolIE-ID ::= 175
	id-GUAMIType											ProtocolIE-ID ::= 176
	id-SRVCCOperationPossible								ProtocolIE-ID ::= 177
	id-TargetRNC-ID											ProtocolIE-ID ::= 178
	id-RAT-Information										ProtocolIE-ID ::= 179
	id-ExtendedRATRestrictionInformation					ProtocolIE-ID ::= 180
	id-QosMonitoringRequest									ProtocolIE-ID ::= 181
	id-SgNB-UE-X2AP-ID										ProtocolIE-ID ::= 182
	id-AdditionalRedundantDL-NGU-UP-TNLInformation			ProtocolIE-ID ::= 183
	id-AdditionalRedundantDLQosFlowPerTNLInformation		ProtocolIE-ID ::= 184
	id-AdditionalRedundantNGU-UP-TNLInformation				ProtocolIE-ID ::= 185
	id-AdditionalRedundantUL-NGU-UP-TNLInformation			ProtocolIE-ID ::= 186
	id-CNPacketDelayBudgetDL								ProtocolIE-ID ::= 187
	id-CNPacketDelayBudgetUL								ProtocolIE-ID ::= 188
	id-ExtendedPacketDelayBudget							ProtocolIE-ID ::= 189
	id-RedundantCommonNetworkInstance						ProtocolIE-ID ::= 190
	id-RedundantDL-NGU-TNLInformationReused					ProtocolIE-ID ::= 191
	id-RedundantDL-NGU-UP-TNLInformation					ProtocolIE-ID ::= 192
	id-RedundantDLQosFlowPerTNLInformation					ProtocolIE-ID ::= 193
	id-RedundantQosFlowIndicator							ProtocolIE-ID ::= 194
	id-RedundantUL-NGU-UP-TNLInformation					ProtocolIE-ID ::= 195
	id-TSCTrafficCharacteristics							ProtocolIE-ID ::= 196
	id-RedundantPDUSessionInformation 						ProtocolIE-ID ::= 197
	id-UsedRSNInformation									ProtocolIE-ID ::= 198
	id-IAB-Authorized										ProtocolIE-ID ::= 199
	id-IAB-Supported										ProtocolIE-ID ::= 200
	id-IABNodeIndication									ProtocolIE-ID ::= 201
	id-NB-IoT-PagingDRX										ProtocolIE-ID ::= 202
	id-NB-IoT-Paging-eDRXInfo								ProtocolIE-ID ::= 203
	id-NB-IoT-DefaultPagingDRX								ProtocolIE-ID ::= 204
	id-Enhanced-CoverageRestriction							ProtocolIE-ID ::= 205
	id-Extended-ConnectedTime								ProtocolIE-ID ::= 206
	id-PagingAssisDataforCEcapabUE							ProtocolIE-ID ::= 207
	id-WUS-Assistance-Information							ProtocolIE-ID ::= 208
	id-UE-DifferentiationInfo								ProtocolIE-ID ::= 209
	id-NB-IoT-UEPriority									ProtocolIE-ID ::= 210
	id-UL-CP-SecurityInformation							ProtocolIE-ID ::= 211
	id-DL-CP-SecurityInformation							ProtocolIE-ID ::= 212
	id-TAI													ProtocolIE-ID ::= 213
	id-UERadioCapabilityForPagingOfNB-IoT					ProtocolIE-ID ::= 214
	id-LTEV2XServicesAuthorized								ProtocolIE-ID ::= 215
	id-NRV2XServicesAuthorized								ProtocolIE-ID ::= 216
	id-LTEUESidelinkAggregateMaximumBitrate					ProtocolIE-ID ::= 217
	id-NRUESidelinkAggregateMaximumBitrate					ProtocolIE-ID ::= 218
	id-PC5QoSParameters										ProtocolIE-ID ::= 219
	id-AlternativeQoSParaSetList							ProtocolIE-ID ::= 220
	id-CurrentQoSParaSetIndex								ProtocolIE-ID ::= 221
	id-CEmodeBrestricted									ProtocolIE-ID ::= 222
 	id-EUTRA-PagingeDRXInformation							ProtocolIE-ID ::= 223
	id-CEmodeBSupport-Indicator								ProtocolIE-ID ::= 224
	id-LTEM-Indication										ProtocolIE-ID ::= 225
	id-EndIndication										ProtocolIE-ID ::= 226
	id-EDT-Session											ProtocolIE-ID ::= 227
	id-UECapabilityInfoRequest								ProtocolIE-ID ::= 228
	id-PDUSessionResourceFailedToResumeListRESReq			ProtocolIE-ID ::= 229
	id-PDUSessionResourceFailedToResumeListRESRes			ProtocolIE-ID ::= 230
	id-PDUSessionResourceSuspendListSUSReq					ProtocolIE-ID ::= 231
	id-PDUSessionResourceResumeListRESReq					ProtocolIE-ID ::= 232
	id-PDUSessionResourceResumeListRESRes					ProtocolIE-ID ::= 233
	id-UE-UP-CIoT-Support									ProtocolIE-ID ::= 234
	id-Suspend-Request-Indication							ProtocolIE-ID ::= 235
	id-Suspend-Response-Indication							ProtocolIE-ID ::= 236
	id-RRC-Resume-Cause										ProtocolIE-ID ::= 237
	id-RGLevelWirelineAccessCharacteristics					ProtocolIE-ID ::= 238
	id-W-AGFIdentityInformation								ProtocolIE-ID ::= 239
	id-GlobalTNGF-ID										ProtocolIE-ID ::= 240
	id-GlobalTWIF-ID										ProtocolIE-ID ::= 241
	id-GlobalW-AGF-ID										ProtocolIE-ID ::= 242
	id-UserLocationInformationW-AGF							ProtocolIE-ID ::= 243
	id-UserLocationInformationTNGF							ProtocolIE-ID ::= 244
	id-AuthenticatedIndication								ProtocolIE-ID ::= 245
	id-TNGFIdentityInformation								ProtocolIE-ID ::= 246
	id-TWIFIdentityInformation								ProtocolIE-ID ::= 247
	id-UserLocationInformationTWIF							ProtocolIE-ID ::= 248
	id-DataForwardingResponseERABList						ProtocolIE-ID ::= 249
	id-IntersystemSONConfigurationTransferDL				ProtocolIE-ID ::= 250
	id-IntersystemSONConfigurationTransferUL				ProtocolIE-ID ::= 251
	id-SONInformationReport									ProtocolIE-ID ::= 252
	id-UEHistoryInformationFromTheUE						ProtocolIE-ID ::= 253
	id-ManagementBasedMDTPLMNList							ProtocolIE-ID ::= 254
	id-MDTConfiguration										ProtocolIE-ID ::= 255
	id-PrivacyIndicator										ProtocolIE-ID ::= 256
	id-TraceCollectionEntityURI								ProtocolIE-ID ::= 257
	id-NPN-Support											ProtocolIE-ID ::= 258
	id-NPN-AccessInformation								ProtocolIE-ID ::= 259
	id-NPN-PagingAssistanceInformation						ProtocolIE-ID ::= 260
	id-NPN-MobilityInformation								ProtocolIE-ID ::= 261
	id-TargettoSource-Failure-TransparentContainer			ProtocolIE-ID ::= 262
	id-NID													ProtocolIE-ID ::= 263
	id-UERadioCapabilityID									ProtocolIE-ID ::= 264
	id-UERadioCapability-EUTRA-Format						ProtocolIE-ID ::= 265
	id-DAPSRequestInfo									ProtocolIE-ID ::= 266
	id-DAPSResponseInfoList								ProtocolIE-ID ::= 267
	id-EarlyStatusTransfer-TransparentContainer 			ProtocolIE-ID ::= 268
	id-NotifySourceNGRANNode								ProtocolIE-ID ::= 269
	id-ExtendedSliceSupportList								ProtocolIE-ID ::= 270
	id-ExtendedTAISliceSupportList							ProtocolIE-ID ::= 271
	id-ConfiguredTACIndication								ProtocolIE-ID ::= 272
	id-Extended-RANNodeName									ProtocolIE-ID ::= 273
	id-Extended-AMFName										ProtocolIE-ID ::= 274
	id-GlobalCable-ID										ProtocolIE-ID ::= 275
	id-QosMonitoringReportingFrequency						ProtocolIE-ID ::= 276
	id-QosFlowParametersList								ProtocolIE-ID ::= 277
	id-QosFlowFeedbackList									ProtocolIE-ID ::= 278
	id-BurstArrivalTimeDownlink								ProtocolIE-ID ::= 279
	id-ExtendedUEIdentityIndexValue							ProtocolIE-ID ::= 280
	id-PduSessionExpectedUEActivityBehaviour				ProtocolIE-ID ::= 281
	id-MicoAllPLMN											ProtocolIE-ID ::= 282
	id-QosFlowFailedToSetupList								ProtocolIE-ID ::= 283
	id-SourceTNLAddrInfo									ProtocolIE-ID ::= 284
	id-ExtendedReportIntervalMDT							ProtocolIE-ID ::= 285
	id-SourceNodeID											ProtocolIE-ID ::= 286
	id-NRNTNTAIInformation									ProtocolIE-ID ::= 287
	id-UEContextReferenceAtSource							ProtocolIE-ID ::= 288
	id-LastVisitedPSCellList								ProtocolIE-ID ::= 289
	id-IntersystemSONInformationRequest						ProtocolIE-ID ::= 290
	id-IntersystemSONInformationReply						ProtocolIE-ID ::= 291
	id-EnergySavingIndication								ProtocolIE-ID ::= 292
	id-IntersystemResourceStatusUpdate						ProtocolIE-ID ::= 293
	id-SuccessfulHandoverReportList							ProtocolIE-ID ::= 294
	id-MBS-AreaSessionID 									ProtocolIE-ID ::= 295
	id-MBS-QoSFlowsToBeSetupList							ProtocolIE-ID ::= 296
	id-MBS-QoSFlowsToBeSetupModList							ProtocolIE-ID ::= 297
	id-MBS-ServiceArea 										ProtocolIE-ID ::= 298
	id-MBS-SessionID 										ProtocolIE-ID ::= 299
	id-MBS-DistributionReleaseRequestTransfer				ProtocolIE-ID ::= 300
	id-MBS-DistributionSetupRequestTransfer 				ProtocolIE-ID ::= 301
	id-MBS-DistributionSetupResponseTransfer				ProtocolIE-ID ::= 302
	id-MBS-DistributionSetupUnsuccessfulTransfer			ProtocolIE-ID ::= 303
	id-MulticastSessionActivationRequestTransfer			ProtocolIE-ID ::= 304
	id-MulticastSessionDeactivationRequestTransfer			ProtocolIE-ID ::= 305
	id-MulticastSessionUpdateRequestTransfer				ProtocolIE-ID ::= 306
	id-MulticastGroupPagingAreaList							ProtocolIE-ID ::= 307
	id-MBS-SupportIndicator									ProtocolIE-ID ::= 309
	id-MBSSessionFailedtoSetupList							ProtocolIE-ID ::= 310
	id-MBSSessionFailedtoSetuporModifyList					ProtocolIE-ID ::= 311
	id-MBSSessionSetupResponseList							ProtocolIE-ID ::= 312
	id-MBSSessionSetuporModifyResponseList					ProtocolIE-ID ::= 313
	id-MBSSessionSetupFailureTransfer						ProtocolIE-ID ::= 314
	id-MBSSessionSetupRequestTransfer						ProtocolIE-ID ::= 315
	id-MBSSessionSetupResponseTransfer						ProtocolIE-ID ::= 316
	id-MBSSessionToReleaseList								ProtocolIE-ID ::= 317
	id-MBSSessionSetupRequestList 							ProtocolIE-ID ::= 318
	id-MBSSessionSetuporModifyRequestList 					ProtocolIE-ID ::= 319
	id-MBS-ActiveSessionInformation-SourcetoTargetList		ProtocolIE-ID ::= 323
	id-MBS-ActiveSessionInformation-TargettoSourceList		ProtocolIE-ID ::= 324
	id-OnboardingSupport									ProtocolIE-ID ::= 325
	id-TimeSyncAssistanceInfo								ProtocolIE-ID ::= 326
	id-SurvivalTime											ProtocolIE-ID ::= 327
	id-QMCConfigInfo										ProtocolIE-ID ::= 328
	id-QMCDeactivation										ProtocolIE-ID ::= 329
	id-PDUSessionPairID										ProtocolIE-ID ::= 331
	id-NR-PagingeDRXInformation								ProtocolIE-ID ::= 332
	id-RedCapIndication										ProtocolIE-ID ::= 333
	id-TargetNSSAIInformation								ProtocolIE-ID ::= 334
	id-UESliceMaximumBitRateList							ProtocolIE-ID ::= 335
	id-M4ReportAmount										ProtocolIE-ID ::= 336
	id-M5ReportAmount										ProtocolIE-ID ::= 337
	id-M6ReportAmount										ProtocolIE-ID ::= 338
	id-M7ReportAmount										ProtocolIE-ID ::= 339
	id-IncludeBeamMeasurementsIndication					ProtocolIE-ID ::= 340
	id-ExcessPacketDelayThresholdConfiguration				ProtocolIE-ID ::= 341
	id-PagingCause											ProtocolIE-ID ::= 342
	id-PagingCauseIndicationForVoiceService					ProtocolIE-ID ::= 343
	id-PEIPSassistanceInformation							ProtocolIE-ID ::= 344
	id-FiveG-ProSeAuthorized								ProtocolIE-ID ::= 345
	id-FiveG-ProSeUEPC5AggregateMaximumBitRate				ProtocolIE-ID ::= 346
	id-FiveG-ProSePC5QoSParameters							ProtocolIE-ID ::= 347
	id-MBSSessionModificationFailureTransfer				ProtocolIE-ID ::= 348
	id-MBSSessionModificationRequestTransfer				ProtocolIE-ID ::= 349
	id-MBSSessionModificationResponseTransfer				ProtocolIE-ID ::= 350
	id-MBS-QoSFlowToReleaseList								ProtocolIE-ID ::= 351
	id-MBS-SessionTNLInfo5GC								ProtocolIE-ID ::= 352
	id-TAINSAGSupportList									ProtocolIE-ID ::= 353
	id-SourceNodeTNLAddrInfo								ProtocolIE-ID ::= 354
	id-NGAPIESupportInformationRequestList					ProtocolIE-ID ::= 355
	id-NGAPIESupportInformationResponseList					ProtocolIE-ID ::= 356
	id-MBS-SessionFSAIDList									ProtocolIE-ID ::= 357
	id-MBSSessionReleaseResponseTransfer					ProtocolIE-ID ::= 358
	id-ManagementBasedMDTPLMNModificationList				ProtocolIE-ID ::= 359
	id-EarlyMeasurement										ProtocolIE-ID ::= 360
	id-BeamMeasurementsReportConfiguration					ProtocolIE-ID ::= 361
	id-HFCNode-ID-new										ProtocolIE-ID ::= 362
	id-GlobalCable-ID-new									ProtocolIE-ID ::= 363
	id-TargetHomeENB-ID										ProtocolIE-ID ::= 364
	id-HashedUEIdentityIndexValue							ProtocolIE-ID ::= 365
	id-ExtendedMobilityInformation							ProtocolIE-ID ::= 366
	id-NetworkControlledRepeaterAuthorized					ProtocolIE-ID ::= 367
	id-AdditionalCancelledlocationReportingReferenceIDList	ProtocolIE-ID ::= 368
	id-Selected-Target-SNPN-Identity						ProtocolIE-ID ::= 369
	id-EquivalentSNPNsList                                  ProtocolIE-ID ::= 370
	id-SelectedNID											ProtocolIE-ID ::= 371
	id-SupportedUETypeList									ProtocolIE-ID ::= 372
	id-AerialUEsubscriptionInformation						ProtocolIE-ID ::= 373
	id-NR-A2X-ServicesAuthorized							ProtocolIE-ID ::= 374
	id-LTE-A2X-ServicesAuthorized							ProtocolIE-ID ::= 375
	id-NR-A2X-UE-PC5-AggregateMaximumBitRate				ProtocolIE-ID ::= 376
	id-LTE-A2X-UE-PC5-AggregateMaximumBitRate				ProtocolIE-ID ::= 377
	id-A2X-PC5-QoS-Parameters								ProtocolIE-ID ::= 378
	id-FiveGProSeLayer2Multipath							ProtocolIE-ID ::= 379
	id-FiveGProSeLayer2UEtoUERelay							ProtocolIE-ID ::= 380
	id-FiveGProSeLayer2UEtoUERemote							ProtocolIE-ID ::= 381
	id-CandidateRelayUEInformationList						ProtocolIE-ID ::= 382
	id-SuccessfulPSCellChangeReportList						ProtocolIE-ID ::= 383
	id-IntersystemMobilityFailureforVoiceFallback			ProtocolIE-ID ::= 384
	id-TargetCellCRNTI                                      ProtocolIE-ID ::= 385
	id-TimeSinceFailure                                     ProtocolIE-ID ::= 386
	id-RANTimingSynchronisationStatusInfo					ProtocolIE-ID ::= 387
	id-RAN-TSSRequestType									ProtocolIE-ID ::= 388
	id-RAN-TSSScope											ProtocolIE-ID ::= 389
	id-ClockQualityReportingControlInfo						ProtocolIE-ID ::= 390
	id-RANfeedbacktype										ProtocolIE-ID ::= 391
	id-QoSFlowTSCList										ProtocolIE-ID ::= 392
	id-TSCTrafficCharacteristicsFeedback					ProtocolIE-ID ::= 393
	id-DownlinkTLContainer									ProtocolIE-ID ::= 394
	id-UplinkTLContainer									ProtocolIE-ID ::= 395
	id-ANPacketDelayBudgetUL								ProtocolIE-ID ::= 396
	id-QosFlowAdditionalInfoList							ProtocolIE-ID ::= 397
	id-AssistanceInformationQoE-Meas						ProtocolIE-ID ::= 398
	id-CommServiceType									ProtocolIE-ID ::= 399
	id-MobileIAB-Authorized									ProtocolIE-ID ::= 400
	id-MobileIAB-MTUserLocationInformation					ProtocolIE-ID ::= 401
	id-MobileIABNodeIndication							    ProtocolIE-ID ::= 402
	id-NoPDUSessionIndication 								ProtocolIE-ID ::= 403
	id-MobileIAB-Supported							        ProtocolIE-ID ::= 404
	id-CN-MT-CommunicationHandling							ProtocolIE-ID ::= 405
	id-FiveGCAction											ProtocolIE-ID ::= 406
	id-PagingPolicyDifferentiation							ProtocolIE-ID ::= 407
	id-DL-Signalling										ProtocolIE-ID ::= 408
	id-PNI-NPN-AreaScopeofMDT								ProtocolIE-ID ::= 409
	id-PNI-NPNBasedMDT										ProtocolIE-ID ::= 410
	id-SNPN-CellBasedMDT									ProtocolIE-ID ::= 411
	id-SNPN-TAIBasedMDT										ProtocolIE-ID ::= 412
	id-SNPN-BasedMDT										ProtocolIE-ID ::= 413
	id-Partially-Allowed-NSSAI								ProtocolIE-ID ::= 414
	id-AssociatedSessionID									ProtocolIE-ID ::= 415
	id-MBS-AssistanceInformation							ProtocolIE-ID ::= 416
	id-BroadcastTransportFailureTransfer					ProtocolIE-ID ::= 417
	id-BroadcastTransportRequestTransfer					ProtocolIE-ID ::= 418
	id-BroadcastTransportResponseTransfer					ProtocolIE-ID ::= 419
	id-TimeBasedHandoverInformation							ProtocolIE-ID ::= 420
	id-DLDiscarding											ProtocolIE-ID ::= 421
	id-PDUsetQoSParameters									ProtocolIE-ID ::= 422
	id-PDUSetbasedHandlingIndicator							ProtocolIE-ID ::= 423
	id-N6JitterInformation									ProtocolIE-ID ::= 424
	id-ECNMarkingorCongestionInformationReportingRequest	ProtocolIE-ID ::= 425
	id-ECNMarkingorCongestionInformationReportingStatus		ProtocolIE-ID ::= 426
	id-ERedCapIndication									ProtocolIE-ID ::= 427
	id-XrDeviceWith2Rx										ProtocolIE-ID ::= 428
	id-UserPlaneErrorIndicator								ProtocolIE-ID ::= 429
	id-SLPositioningRangingServiceInfo						ProtocolIE-ID ::= 430
	id-PDUSessionListMTCommHReq								ProtocolIE-ID ::= 431
	id-MaximumDataBurstVolume 								ProtocolIE-ID ::= 432
	id-MN-only-MDT-collection								ProtocolIE-ID ::= 433
	id-MBS-NGUFailureIndication								ProtocolIE-ID ::= 434
	id-UserPlaneFailureIndication							ProtocolIE-ID ::= 435
	id-UserPlaneFailureIndicationReport						ProtocolIE-ID ::= 436
	id-SourceSN-to-TargetSN-QMCInfo							ProtocolIE-ID ::= 437
	id-QoERVQoEReportingPaths								ProtocolIE-ID ::= 438
	id-UserLocationInformationN3IWF-without-PortNumber		ProtocolIE-ID ::= 439
	id-AUN3DeviceAccessInfo									ProtocolIE-ID ::= 440
	id-TAIMBSSupportList									ProtocolIE-ID ::= 441
	id-ExtendedBackupAMFName    							ProtocolIE-ID ::= 442
	id-ExtendedOldAMF			    						ProtocolIE-ID ::= 443
	id-MBS-UP-FailureIndication 							ProtocolIE-ID ::= 444
	id-RequestedTNLInfo										ProtocolIE-ID ::= 445
	id-Aerial-UE-FlightInformationOngoingReporting-failed	ProtocolIE-ID ::= 446
	id-NetworkSliceAreaScopeofMDT							ProtocolIE-ID ::= 447
	id-GeographyBasedMDT									ProtocolIE-ID ::= 448
	id-MBS-IntendedServiceAreaList							ProtocolIE-ID ::= 449
	id-AMF-UE-NGAP-ID2										ProtocolIE-ID ::= 450
	id-GUAMIList											ProtocolIE-ID ::= 451
	id-GW-Context-Release-Indication						ProtocolIE-ID ::= 452
	id-SourceAMF-GUAMI										ProtocolIE-ID ::= 453
	id-RequestedNSSAI										ProtocolIE-ID ::= 454
	id-Target-RAN-Node-ID									ProtocolIE-ID ::= 455
	id-InventoryRequestTransfer							ProtocolIE-ID ::= 456
	id-InventoryResponseTransfer						ProtocolIE-ID ::= 457
	id-InventoryFailureTransfer							ProtocolIE-ID ::= 458
	id-InventoryReportTransfer							ProtocolIE-ID ::= 459
	id-CommandRequestTransfer							ProtocolIE-ID ::= 460
	id-CommandResponseTransfer							ProtocolIE-ID ::= 461
	id-CommandFailureTransfer							ProtocolIE-ID ::= 462
	id-AIOTSessionReleaseCommandTransfer					ProtocolIE-ID ::= 463
	id-AIOTSessionReleaseCompleteTransfer					ProtocolIE-ID ::= 464
	id-AIOTSessionReleaseRequestTransfer				ProtocolIE-ID ::= 465
	id-AIoT-CorrelationIdentifier							ProtocolIE-ID ::= 466
	id-AIOTFIdentifier									ProtocolIE-ID ::= 467
	id-AIoT-DeviceIdentificationRequested					ProtocolIE-ID ::= 468
	id-AIoT-RequestedServiceAreaInformation					ProtocolIE-ID ::= 469
	id-AIoT-InventoryAssistanceInformation					ProtocolIE-ID ::= 470
	id-AIoT-FollowonCommandIndication						ProtocolIE-ID ::= 471
	id-RAN-AIOT-Device-NGAP-ID								ProtocolIE-ID ::= 472
	id-AIoT-CommandAssistanceInformation					ProtocolIE-ID ::= 473
	id-AIoT-NASPDU										ProtocolIE-ID ::= 474
	id-AIoT-Support											ProtocolIE-ID ::= 475
	id-AIOTFName											ProtocolIE-ID ::= 476
	id-LPWUSPSAssistanceInformation							ProtocolIE-ID ::= 477
	id-FurtherExtendedUEIdentityIndexValue					ProtocolIE-ID ::= 478
	id-FiveGProSeLayer2MHUEtoNetworkRelay					ProtocolIE-ID ::= 479
	id-FiveGProSeLayer2MHIntermediateUEtoNetworkRelay		ProtocolIE-ID ::= 480
	id-FiveGProSeLayer2MHRemote								ProtocolIE-ID ::= 481
	id-FiveGProSeLayer3MHUEtoNetworkRelay					ProtocolIE-ID ::= 482
	id-AdditionalULI										ProtocolIE-ID ::= 483
	id-PduSetDelayBudgetDownlink							ProtocolIE-ID ::= 484
	id-PduSetDelayBudgetUplink								ProtocolIE-ID ::= 485
	id-PduSetErrorRateDownlink								ProtocolIE-ID ::= 486
	id-PduSetErrorRateUplink								ProtocolIE-ID ::= 487
	id-DLPDUSetInformationMarkingSupportIndication			ProtocolIE-ID ::= 488
	id-MonitoringRequestonAvailableBitrate					ProtocolIE-ID ::= 489
	id-MMSID												ProtocolIE-ID ::= 490
	id-Indication-of-Bitrate-Adaptation						ProtocolIE-ID ::= 491
	id-SCGActivationTime									ProtocolIE-ID ::= 492
	id-Aerial-UE-FlightInformationReporting					ProtocolIE-ID ::= 493
	id-Aerial-UE-FlightInformationReportingControlList		ProtocolIE-ID ::= 494
	id-LPWUSDisableIndication								ProtocolIE-ID ::= 495
	id-AIoT-SecurityInfo									ProtocolIE-ID ::= 496




END
